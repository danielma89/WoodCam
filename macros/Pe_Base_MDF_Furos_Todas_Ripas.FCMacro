# -*- coding: utf-8 -*-
# FreeCAD Macro: Pe_Base_MDF_com_Furos.FCMacro
#
# Base/pé retangular de MDF:
# - 4 ripas perimetrais
# - N ripas internas distribuídas automaticamente
# - furação opcional nas faces externas da FRENTE e do FUNDO
# - os furos ficam alinhados às 2 laterais + todas as ripas internas, nos dois lados
# - quantidade de furos POR RIPA configurável
#
# Eixos:
# X = largura
# Y = profundidade
# Z = altura

import FreeCAD as App
import Part

try:
    from PySide import QtCore
    try:
        from PySide import QtWidgets
    except ImportError:
        from PySide import QtGui as QtWidgets
except Exception:
    from PySide2 import QtCore, QtWidgets


class PeMDFDialog(QtWidgets.QDialog):
    def __init__(self):
        super(PeMDFDialog, self).__init__()
        self.setWindowTitle("Criar pé/base de MDF - furos frente e fundo")
        self.setMinimumWidth(430)

        layout = QtWidgets.QVBoxLayout(self)

        # ---------- DIMENSÕES ----------
        dim_group = QtWidgets.QGroupBox("Dimensões")
        dim_form = QtWidgets.QFormLayout(dim_group)

        self.largura = self._spin(100.0, 5000.0, 600.0)
        self.profundidade = self._spin(100.0, 5000.0, 500.0)
        self.altura = self._spin(20.0, 1000.0, 100.0)
        self.espessura = self._spin(3.0, 100.0, 15.0)

        self.ripas = QtWidgets.QSpinBox()
        self.ripas.setRange(0, 50)
        self.ripas.setValue(3)

        self.orientacao = QtWidgets.QComboBox()
        self.orientacao.addItem("Frente ↔ Fundo", "Y")
        self.orientacao.addItem("Esquerda ↔ Direita", "X")

        dim_form.addRow("Largura total:", self.largura)
        dim_form.addRow("Profundidade total:", self.profundidade)
        dim_form.addRow("Altura do pé:", self.altura)
        dim_form.addRow("Espessura MDF:", self.espessura)
        dim_form.addRow("Ripas internas:", self.ripas)
        dim_form.addRow("Sentido das ripas:", self.orientacao)

        layout.addWidget(dim_group)

        # ---------- FURAÇÃO ----------
        hole_group = QtWidgets.QGroupBox("Furação das faces frontal e traseira")
        hole_form = QtWidgets.QFormLayout(hole_group)

        self.criar_furos = QtWidgets.QCheckBox("Criar furos na frente e no fundo, alinhados a todas as ripas")
        self.criar_furos.setChecked(True)

        self.furos_por_ripa = QtWidgets.QSpinBox()
        self.furos_por_ripa.setRange(1, 10)
        self.furos_por_ripa.setValue(1)

        self.diametro_furo = self._spin(1.0, 30.0, 5.0)
        self.margem_furo = self._spin(1.0, 200.0, 20.0)

        hole_form.addRow(self.criar_furos)
        hole_form.addRow("Furos por ripa:", self.furos_por_ripa)
        hole_form.addRow("Diâmetro do furo:", self.diametro_furo)
        hole_form.addRow("Margem sup./inf.:", self.margem_furo)

        hole_info = QtWidgets.QLabel(
            "Os furos são feitos nas faces externas da peça FRONTAL e da peça FUNDO, "
            "alinhados às duas laterais e a todas as ripas internas. Com 1 furo por ripa, ele fica "
            "centralizado na altura. Com 2 ou mais, são distribuídos verticalmente."
        )
        hole_info.setWordWrap(True)

        hole_v = QtWidgets.QVBoxLayout()
        hole_v.addWidget(hole_group)
        hole_v.addWidget(hole_info)
        layout.addLayout(hole_v)

        # ---------- OPÇÕES ----------
        self.criar_planilha = QtWidgets.QCheckBox("Criar lista de corte")
        self.criar_planilha.setChecked(True)

        self.agrupar = QtWidgets.QCheckBox("Agrupar peças")
        self.agrupar.setChecked(True)

        layout.addWidget(self.criar_planilha)
        layout.addWidget(self.agrupar)

        warning = QtWidgets.QLabel(
            "Obs.: a furação nas peças frente/fundo é aplicável quando as ripas internas estão "
            "no sentido Frente ↔ Fundo, pois são elas que encostam nas duas travessas."
        )
        warning.setWordWrap(True)
        layout.addWidget(warning)

        buttons = QtWidgets.QDialogButtonBox(
            QtWidgets.QDialogButtonBox.Ok |
            QtWidgets.QDialogButtonBox.Cancel
        )
        buttons.accepted.connect(self.accept)
        buttons.rejected.connect(self.reject)
        layout.addWidget(buttons)

    def _spin(self, minimum, maximum, value):
        s = QtWidgets.QDoubleSpinBox()
        s.setRange(minimum, maximum)
        s.setDecimals(1)
        s.setSingleStep(1.0)
        s.setValue(value)
        s.setSuffix(" mm")
        return s


def combo_data(combo):
    """Compatibilidade entre versões diferentes de PySide/Qt."""
    try:
        return combo.currentData()
    except Exception:
        return combo.itemData(combo.currentIndex())


def unique_name(doc, base):
    name = base
    i = 1
    while doc.getObject(name):
        i += 1
        name = "{}_{:02d}".format(base, i)
    return name


def add_board(doc, container, name, label, shape, comp, altura, esp):
    obj = doc.addObject("Part::Feature", name)
    obj.Label = label
    obj.Shape = shape

    obj.addProperty("App::PropertyLength", "Comprimento", "MDF")
    obj.addProperty("App::PropertyLength", "AlturaPeca", "MDF")
    obj.addProperty("App::PropertyLength", "EspessuraPeca", "MDF")
    obj.Comprimento = comp
    obj.AlturaPeca = altura
    obj.EspessuraPeca = esp

    if container is not None:
        container.addObject(obj)

    try:
        obj.ViewObject.ShapeColor = (0.82, 0.67, 0.44)
    except Exception:
        pass

    return obj


def hole_z_positions(height, qty, margin):
    """
    Retorna alturas Z dos centros.
    1 furo -> centro.
    >=2 -> distribuição uniforme entre as margens.
    """
    if qty <= 1:
        return [height / 2.0]

    m = max(0.0, min(margin, height / 2.0 - 0.1))
    low = m
    high = height - m

    if high <= low:
        return [height / 2.0 for _ in range(qty)]

    step = (high - low) / float(qty - 1)
    return [low + i * step for i in range(qty)]


def cut_front_holes(front_shape, x_centers, height, thickness,
                    qty_per_ripa, diameter, margin):
    """
    Fura a peça frontal no eixo Y.
    A face externa frontal está em Y=0.
    Cilindro atravessa toda a espessura da peça frontal.
    """
    result = front_shape
    radius = diameter / 2.0
    eps = 1.0
    z_positions = hole_z_positions(height, qty_per_ripa, margin)

    for x in x_centers:
        for z in z_positions:
            tool = Part.makeCylinder(
                radius,
                thickness + 2.0 * eps,
                App.Vector(x, -eps, z),
                App.Vector(0, 1, 0)
            )
            result = result.cut(tool)

    return result, z_positions


def create_cutlist(doc, parent_name, rows):
    sheet_name = unique_name(doc, parent_name + "_ListaCorte")
    sheet = doc.addObject("Spreadsheet::Sheet", sheet_name)
    sheet.Label = "Lista de corte - " + parent_name

    headers = ["Peça", "Qtd.", "Comprimento (mm)", "Altura (mm)", "Espessura (mm)"]
    for col, value in zip(["A", "B", "C", "D", "E"], headers):
        sheet.set(col + "1", value)

    for i, row in enumerate(rows, start=2):
        sheet.set("A{}".format(i), str(row["nome"]))
        sheet.set("B{}".format(i), str(row["qtd"]))
        sheet.set("C{}".format(i), str(round(row["comp"], 2)))
        sheet.set("D{}".format(i), str(round(row["altura"], 2)))
        sheet.set("E{}".format(i), str(round(row["esp"], 2)))

    try:
        sheet.setStyle("A1:E1", "bold", "add")
        sheet.setColumnWidth("A", 220)
        sheet.setColumnWidth("B", 70)
        sheet.setColumnWidth("C", 130)
        sheet.setColumnWidth("D", 110)
        sheet.setColumnWidth("E", 110)
    except Exception:
        pass

    return sheet


def build_base():
    dlg = PeMDFDialog()
    if dlg.exec_() != QtWidgets.QDialog.Accepted:
        return

    W = float(dlg.largura.value())
    D = float(dlg.profundidade.value())
    H = float(dlg.altura.value())
    T = float(dlg.espessura.value())
    N = int(dlg.ripas.value())
    direction = combo_data(dlg.orientacao)

    holes_enabled = dlg.criar_furos.isChecked()
    holes_per_ripa = int(dlg.furos_por_ripa.value())
    hole_dia = float(dlg.diametro_furo.value())
    hole_margin = float(dlg.margem_furo.value())

    if W <= 2 * T or D <= 2 * T:
        QtWidgets.QMessageBox.critical(
            None,
            "Dimensões inválidas",
            "Largura e profundidade precisam ser maiores que 2x a espessura do MDF."
        )
        return

    if hole_dia >= H:
        QtWidgets.QMessageBox.critical(
            None,
            "Furo inválido",
            "O diâmetro do furo precisa ser menor que a altura do pé."
        )
        return

    doc = App.ActiveDocument
    if doc is None:
        doc = App.newDocument("Pe_MDF")

    base_id = unique_name(doc, "Pe_MDF")

    container = None
    if dlg.agrupar.isChecked():
        container = doc.addObject("App::Part", base_id)
        container.Label = "Pé MDF {} x {} x {}".format(
            int(round(W)), int(round(D)), int(round(H))
        )

        container.addProperty("App::PropertyLength", "LarguraTotal", "Parametros")
        container.addProperty("App::PropertyLength", "ProfundidadeTotal", "Parametros")
        container.addProperty("App::PropertyLength", "Altura", "Parametros")
        container.addProperty("App::PropertyLength", "EspessuraMDF", "Parametros")
        container.addProperty("App::PropertyInteger", "RipasInternas", "Parametros")
        container.addProperty("App::PropertyString", "OrientacaoRipas", "Parametros")

        container.LarguraTotal = W
        container.ProfundidadeTotal = D
        container.Altura = H
        container.EspessuraMDF = T
        container.RipasInternas = N
        container.OrientacaoRipas = (
            "Frente-Fundo" if direction == "Y" else "Esquerda-Direita"
        )

        container.addProperty("App::PropertyBool", "FurosFrenteFundo", "Furacao")
        container.addProperty("App::PropertyInteger", "FurosPorRipa", "Furacao")
        container.addProperty("App::PropertyLength", "DiametroFuro", "Furacao")
        container.addProperty("App::PropertyLength", "MargemVerticalFuros", "Furacao")

        container.FurosFrenteFundo = bool(holes_enabled)
        container.FurosPorRipa = holes_per_ripa
        container.DiametroFuro = hole_dia
        container.MargemVerticalFuros = hole_margin

    # ---------------------------------------------------------
    # Calcula centros das ripas antes de criar a peça frontal,
    # pois a furação usa exatamente esses mesmos centros.
    # ---------------------------------------------------------
    internal_specs = []
    internal_x_centers = []

    if N > 0:
        if direction == "Y":
            usable = W - 2 * T
            step = usable / float(N + 1)

            for i in range(1, N + 1):
                center_x = T + step * i
                x = center_x - T / 2.0

                internal_x_centers.append(center_x)
                internal_specs.append({
                    "i": i,
                    "dx": T,
                    "dy": D - 2 * T,
                    "x": x,
                    "y": T,
                    "comp": D - 2 * T,
                })
        else:
            usable = D - 2 * T
            step = usable / float(N + 1)

            for i in range(1, N + 1):
                center_y = T + step * i
                y = center_y - T / 2.0

                internal_specs.append({
                    "i": i,
                    "dx": W - 2 * T,
                    "dy": T,
                    "x": T,
                    "y": y,
                    "comp": W - 2 * T,
                })

    # ---------------------------------------------------------
    # EIXOS DE FURAÇÃO
    # ---------------------------------------------------------
    # Além das ripas internas, as duas laterais também encostam
    # na frente e no fundo. Portanto elas também recebem furação.
    #
    # Centros:
    # - lateral esquerda: T/2
    # - ripas internas: centros calculados acima
    # - lateral direita: W - T/2
    all_ripa_x_centers = []

    if direction == "Y":
        all_ripa_x_centers = [T / 2.0]
        all_ripa_x_centers.extend(internal_x_centers)
        all_ripa_x_centers.append(W - T / 2.0)

    # ---------------------------------------------------------
    # PEÇA FRONTAL
    # ---------------------------------------------------------
    front_shape = Part.makeBox(W, T, H)

    z_positions = []
    actual_end_holes = (
        holes_enabled and
        direction == "Y" and
        N > 0
    )

    if actual_end_holes:
        front_shape, z_positions = cut_front_holes(
            front_shape,
            all_ripa_x_centers,
            H,
            T,
            holes_per_ripa,
            hole_dia,
            hole_margin
        )

    front = add_board(
        doc, container,
        base_id + "_Frente",
        "Frente - FURADA" if actual_end_holes else "Frente",
        front_shape,
        W, H, T
    )

    # Propriedades específicas na peça frontal
    front.addProperty("App::PropertyInteger", "QuantidadeFuros", "Furacao")
    front.addProperty("App::PropertyLength", "DiametroFuros", "Furacao")
    front.addProperty("App::PropertyString", "AlinhamentoFuros", "Furacao")

    front.QuantidadeFuros = (
        len(all_ripa_x_centers) * holes_per_ripa if actual_end_holes else 0
    )
    front.DiametroFuros = hole_dia
    front.AlinhamentoFuros = (
        "Eixo das laterais + ripas internas" if actual_end_holes else "Sem furacao"
    )

    # ---------------------------------------------------------
    # FUNDO
    # ---------------------------------------------------------
    # Para manter exatamente o mesmo alinhamento dos furos da frente,
    # a peça do fundo é furada no sistema local antes de ser deslocada.
    back_shape = Part.makeBox(W, T, H)

    if actual_end_holes:
        # Furação atravessando a espessura da travessa do fundo.
        # Usa os MESMOS centros X e Z da peça frontal.
        radius = hole_dia / 2.0
        eps = 1.0
        for x in all_ripa_x_centers:
            for z in z_positions:
                tool = Part.makeCylinder(
                    radius,
                    T + 2.0 * eps,
                    App.Vector(x, -eps, z),
                    App.Vector(0, 1, 0)
                )
                back_shape = back_shape.cut(tool)

    back_shape.translate(App.Vector(0, D - T, 0))

    back = add_board(
        doc, container,
        base_id + "_Fundo",
        "Fundo - FURADO" if actual_end_holes else "Fundo",
        back_shape,
        W, H, T
    )

    back.addProperty("App::PropertyInteger", "QuantidadeFuros", "Furacao")
    back.addProperty("App::PropertyLength", "DiametroFuros", "Furacao")
    back.addProperty("App::PropertyString", "AlinhamentoFuros", "Furacao")

    back.QuantidadeFuros = (
        len(all_ripa_x_centers) * holes_per_ripa if actual_end_holes else 0
    )
    back.DiametroFuros = hole_dia
    back.AlinhamentoFuros = (
        "Eixo das laterais + ripas internas" if actual_end_holes else "Sem furacao"
    )

    # ---------------------------------------------------------
    # LATERAIS
    # ---------------------------------------------------------
    lateral_len = D - 2 * T

    left_shape = Part.makeBox(T, lateral_len, H)
    left_shape.translate(App.Vector(0, T, 0))
    add_board(
        doc, container,
        base_id + "_Lateral_E",
        "Lateral esquerda",
        left_shape,
        lateral_len, H, T
    )

    right_shape = Part.makeBox(T, lateral_len, H)
    right_shape.translate(App.Vector(W - T, T, 0))
    add_board(
        doc, container,
        base_id + "_Lateral_D",
        "Lateral direita",
        right_shape,
        lateral_len, H, T
    )

    # ---------------------------------------------------------
    # RIPAS INTERNAS
    # ---------------------------------------------------------
    for spec in internal_specs:
        shape = Part.makeBox(spec["dx"], spec["dy"], H)
        shape.translate(App.Vector(spec["x"], spec["y"], 0))

        add_board(
            doc, container,
            "{}_Ripa_{:02d}".format(base_id, spec["i"]),
            "Ripa interna {:02d}".format(spec["i"]),
            shape,
            spec["comp"], H, T
        )

    # ---------------------------------------------------------
    # LISTA DE CORTE
    # ---------------------------------------------------------
    if dlg.criar_planilha.isChecked():
        rows = [
            {"nome": "Frente/Fundo", "qtd": 2, "comp": W, "altura": H, "esp": T},
            {"nome": "Laterais", "qtd": 2, "comp": D - 2*T, "altura": H, "esp": T},
        ]

        if N > 0:
            rows.append({
                "nome": "Ripas internas",
                "qtd": N,
                "comp": D - 2*T if direction == "Y" else W - 2*T,
                "altura": H,
                "esp": T
            })

        sheet = create_cutlist(doc, base_id, rows)

        if actual_end_holes:
            row = 6
            sheet.set("A{}".format(row), "Furação frente + fundo")
            sheet.set("B{}".format(row), str(2 * (N + 2) * holes_per_ripa))
            sheet.set("C{}".format(row), "Ø {}".format(round(hole_dia, 2)))
            sheet.set("D{}".format(row), "{} por ripa".format(holes_per_ripa))
            sheet.set("E{}".format(row), "alinhado")

        if container is not None:
            container.addObject(sheet)

    doc.recompute()

    try:
        Gui.activeDocument().activeView().viewAxonometric()
        Gui.activeDocument().activeView().fitAll()
    except Exception:
        pass

    msg = (
        "Base criada com sucesso.\n\n"
        "Dimensões: {:.1f} x {:.1f} x {:.1f} mm\n"
        "MDF: {:.1f} mm\n"
        "Ripas internas: {}\n".format(W, D, H, T, N)
    )

    if actual_end_holes:
        msg += (
            "\nFuração frente + fundo:\n"
            "- {} furo(s) por ripa\n"
            "- {} linha(s), alinhadas às ripas\n"
            "- {} furos em cada face\n"            "- {} furos no total (frente + fundo)\n"
            "- Ø {:.1f} mm"
        ).format(
            holes_per_ripa,
            N,
            N * holes_per_ripa,
            2 * N * holes_per_ripa,
            hole_dia
        )
    elif holes_enabled and direction != "Y":
        msg += (
            "\n\nA furação frente/fundo não foi criada porque as ripas estão "
            "no sentido Esquerda ↔ Direita."
        )

    QtWidgets.QMessageBox.information(
        None,
        "Pé MDF criado",
        msg
    )


build_base()
