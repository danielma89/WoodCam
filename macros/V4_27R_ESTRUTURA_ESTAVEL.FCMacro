# -*- coding: utf-8 -*-
"""
Gerador de Estrutura por Esqueleto v4.27Q — travessa interna garantida
=====================================
Compatível com FreeCAD 1.1/1.2.

FONTES ACEITAS
--------------
- Sketcher::SketchObject com segmentos de reta;
- Draft Line;
- Draft Wire / Polyline;
- outros objetos com Shape.Edges retos.

MODOS
-----
1. Automático:
   - procura um ciclo fechado planar entre as linhas;
   - o ciclo é tratado como LIMITE EXTERNO;
   - linhas restantes viram elementos 3D;
   - linhas perpendiculares ligadas aos vértices do ciclo podem virar pernas
     ancoradas no canto externo.

2. Contorno externo planar:
   - exige um único contorno fechado, convexo e planar;
   - preserva exatamente a dimensão externa desenhada;
   - aplica meia-esquadria automática ou extremidades sem aparar.

3. Rede 3D por eixos:
   - cada linha vira um perfil tubular centrado em seu eixo;
   - não calcula ainda os encontros complexos entre três ou mais barras.

EXEMPLO DE MESA
---------------
Desenhe na bancada Draft:
- um retângulo fechado no plano superior;
- quatro linhas verticais, uma em cada vértice.

No modo Automático:
- o retângulo vira o quadro superior com limite externo preservado;
- as quatro linhas verticais viram pernas;
- se ModoPernasCanto = "Ancorar no canto externo", a seção das pernas cresce
  para dentro do retângulo, sem aumentar a dimensão externa.

PERNAS — MODO SEM JUNTA
-----------------------
- a linha da perna continua representando a altura externa total;
- o corpo tubular da perna começa na face inferior do quadro;
- não há colisão entre quadro e perna;
- tampas opcionais: nenhuma, superior, inferior ou ambas;
- com tampa superior, pode ser criado um toco de fixação:
    * uma tampa estrutural de fechamento;
    * três chapas por padrão, com quantidade configurável;
    * o painel inferior das duas travessas é interrompido na quina;
    * o conjunto fica disponível para parafusamento posterior.

OBSERVAÇÃO
----------
Esta versão segura evita Pad e fusões globais do conjunto. Cada painel é mantido
como Part::Feature independente. O quadro horizontal pode ser gerado com dentes
reais e rasgos complementares. Dentes inferiores são redistribuídos em cada vão livre,
rasgos abertos recebem alívio apenas nos cantos internos, as tampas das pernas
podem ser unidas por dentes nas quatro bordas, as paredes das pernas sobem uma
espessura para encaixar no quadro e as raízes dos dentes das costelas recebem
alívio local para CNC. A V4.25 respeita exatamente a seleção atual: selecionar um Sketch processa somente esse Sketch; selecionar um Grupo processa o conteúdo do Grupo. Em Sketch único, toda linha coplanar que não pertence ao perímetro externo é promovida diretamente a travessa segura.
"""

import math
import FreeCAD as App
import Part
import Sketcher

try:
    import FreeCADGui as Gui
except Exception:
    Gui = None


DOC_NAME = "EstruturaEsqueleto"
PARAM_NAME = "Config_Estrutura_Esqueleto_V42"
ROOT_NAME = "Estrutura_Por_Esqueleto_V427"
GENERATOR_TAG = "Gerador_Estrutura_Esqueleto_v4_27R"
TOL = 1e-6
PLANAR_TOL = 1e-4
ANGLE_TOL = 1e-3
# Pairwise intersection is intentionally bounded.  A regular table sketch
# has only a handful of internal members; hundreds indicate trace fragments
# or an accidental selection of generated geometry, not a usable skeleton.
MAX_PLANAR_MEMBER_CANDIDATES = 80


# =============================================================================
# Utilidades básicas
# =============================================================================

def active_or_new_document():
    doc = App.ActiveDocument
    if doc is None:
        doc = App.newDocument(DOC_NAME)
    return doc


def add_property(obj, type_id, name, group, description, default=None):
    created = False
    if name not in obj.PropertiesList:
        obj.addProperty(type_id, name, group, description)
        created = True
    if created and default is not None:
        setattr(obj, name, default)
    return created


def set_read_only(obj, names):
    for name in names:
        try:
            obj.setEditorMode(name, 1)
        except Exception:
            pass


def mark_generated(obj):
    try:
        if "GeradorEstruturaEsqueleto" not in obj.PropertiesList:
            obj.addProperty(
                "App::PropertyString",
                "GeradorEstruturaEsqueleto",
                "Gerador",
                "Identificador interno do gerador.",
            )
        obj.GeradorEstruturaEsqueleto = GENERATOR_TAG
        obj.setEditorMode("GeradorEstruturaEsqueleto", 2)
    except Exception:
        pass


def qvalue(obj, name):
    value = getattr(obj, name)
    return float(value.Value if hasattr(value, "Value") else value)


def vector_distance(a, b):
    return (a.sub(b)).Length


def vector_unit(vector, message="Vetor de comprimento nulo."):
    length = vector.Length
    if length <= TOL:
        raise ValueError(message)
    # FreeCAD.Vector.multiply altera o próprio vetor.  Esta função é usada para
    # construir bases locais a partir de linhas originais; normalizá-las in
    # place podia zerar a direção que seria reutilizada logo em seguida e
    # fazia pernas/travessas 3D serem descartadas como "vetor nulo".
    return App.Vector(vector).multiply(1.0 / length)


def vector_scaled(vector, factor):
    """Escala uma cópia; nunca altera um eixo já guardado no descritor."""
    return App.Vector(vector).multiply(factor)


def clamp(value, lower, upper):
    return max(lower, min(upper, value))


def matrix_placement(origin, axis_x, axis_y, axis_z):
    """Cria Placement usando os três eixos locais como colunas da matriz."""
    matrix = App.Matrix()

    matrix.A11 = axis_x.x
    matrix.A12 = axis_y.x
    matrix.A13 = axis_z.x
    matrix.A14 = origin.x

    matrix.A21 = axis_x.y
    matrix.A22 = axis_y.y
    matrix.A23 = axis_z.y
    matrix.A24 = origin.y

    matrix.A31 = axis_x.z
    matrix.A32 = axis_y.z
    matrix.A33 = axis_z.z
    matrix.A34 = origin.z

    matrix.A41 = 0.0
    matrix.A42 = 0.0
    matrix.A43 = 0.0
    matrix.A44 = 1.0

    return App.Placement(matrix)


# =============================================================================
# Objeto de parâmetros
# =============================================================================

def set_enum(obj, name, values, default):
    try:
        current = str(getattr(obj, name))
    except Exception:
        current = ""

    setattr(obj, name, values)
    if current in values:
        setattr(obj, name, current)
    else:
        setattr(obj, name, default)


def ensure_parameters(doc):
    params = doc.getObject(PARAM_NAME)
    if params is None:
        params = doc.addObject("App::FeaturePython", PARAM_NAME)
    params.Label = "CONFIGURAÇÃO — Estrutura por esqueleto V4.7"

    # ------------------------------------------------------------------
    # 01 — Entrada: o usuário começa escolhendo as linhas.
    # ------------------------------------------------------------------
    add_property(
        params, "App::PropertyLink", "SketchOrigem", "01 — Entrada",
        "Compatibilidade com versões anteriores: Sketch principal."
    )
    add_property(
        params, "App::PropertyLinkList", "ObjetosOrigem", "01 — Entrada",
        "Selecione Sketches, linhas ou polilinhas Draft que formam a estrutura."
    )
    add_property(
        params, "App::PropertyEnumeration", "ModoInterpretacao", "01 — Entrada",
        "Automático procura um quadro fechado e interpreta as demais linhas como pernas ou barras."
    )
    set_enum(
        params,
        "ModoInterpretacao",
        ["Automático", "Somente quadro fechado", "Somente linhas 3D"],
        "Automático",
    )
    add_property(
        params, "App::PropertyLength", "ToleranciaConexao", "01 — Entrada",
        "Distância máxima para considerar uma linha conectada ao quadro.", 0.50
    )

    # ------------------------------------------------------------------
    # 02 — Quadro: dimensões e acabamento das quinas.
    # ------------------------------------------------------------------
    add_property(
        params, "App::PropertyEnumeration", "TipoConexao", "02 — Quadro",
        "Tratamento das quinas do contorno fechado."
    )
    set_enum(
        params,
        "TipoConexao",
        ["Meia-esquadria automática", "Extremidades retas"],
        "Meia-esquadria automática",
    )
    add_property(
        params, "App::PropertyEnumeration", "DirecaoAlturaPlanar", "02 — Quadro",
        "Lado do plano em que a altura do quadro será criada."
    )
    set_enum(
        params,
        "DirecaoAlturaPlanar",
        ["Automática pelas pernas", "Normal do contorno", "Oposta à normal"],
        "Automática pelas pernas",
    )
    add_property(
        params, "App::PropertyLength", "LarguraPerfil", "02 — Quadro",
        "Quanto o quadro cresce para dentro do limite desenhado.", 150.0
    )
    add_property(
        params, "App::PropertyLength", "AlturaPerfil", "02 — Quadro",
        "Altura externa do quadro.", 150.0
    )
    add_property(
        params, "App::PropertyLength", "EspessuraParede", "02 — Quadro",
        "Espessura do MDF ou da chapa usada nas quatro paredes.", 15.0
    )
    add_property(
        params, "App::PropertyLength", "DeslocamentoNormal", "02 — Quadro",
        "Deslocamento opcional na direção normal ao quadro.", 0.0
    )
    add_property(
        params, "App::PropertyLength", "ElevacaoZ", "02 — Quadro",
        "Compatibilidade: deslocamento adicional no eixo Z global.", 0.0
    )

    # ------------------------------------------------------------------
    # 02B — União dos quatro painéis do quadro.
    # ------------------------------------------------------------------
    add_property(
        params, "App::PropertyEnumeration", "UniaoPaineisQuadro", "02B — Dentes do quadro",
        "Lisa mantém as quatro chapas retas. Dentada cria abas nas paredes laterais e rasgos nos painéis superior/inferior."
    )
    set_enum(
        params,
        "UniaoPaineisQuadro",
        ["Lisa", "Dentada"],
        "Dentada",
    )
    add_property(
        params, "App::PropertyLength", "ComprimentoDenteQuadro", "02B — Dentes do quadro",
        "Comprimento de cada dente ao longo da travessa.", 80.0
    )
    add_property(
        params, "App::PropertyLength", "EspacoDentesQuadro", "02B — Dentes do quadro",
        "Espaço livre entre dentes consecutivos.", 80.0
    )
    add_property(
        params, "App::PropertyLength", "ProfundidadeDenteQuadro", "02B — Dentes do quadro",
        "Quanto o dente entra no painel superior/inferior. Zero usa a espessura da chapa.", 0.0
    )
    add_property(
        params, "App::PropertyLength", "MargemDentesQuadro", "02B — Dentes do quadro",
        "Margem adicional depois da zona de meia-esquadria. Evita dentes nas pontas.", 10.0
    )
    add_property(
        params, "App::PropertyLength", "FolgaDentesQuadro", "02B — Dentes do quadro",
        "Folga adicional dos rasgos em relação aos dentes.", 0.15
    )

    # ------------------------------------------------------------------
    # 03 — Pernas: interpretação e tamanho.
    # ------------------------------------------------------------------
    add_property(
        params, "App::PropertyEnumeration", "ModoPernasCanto", "03 — Pernas",
        "No vértice, ancora a seção no canto externo ou centraliza sobre a linha."
    )
    set_enum(
        params,
        "ModoPernasCanto",
        ["Ancorar no canto externo", "Centralizar na linha"],
        "Ancorar no canto externo",
    )
    add_property(
        params, "App::PropertyEnumeration", "ConexaoPernaQuadro", "03 — Pernas",
        "Sem junta faz a perna parar abaixo do quadro. O modo com junta será desenvolvido depois."
    )
    set_enum(
        params,
        "ConexaoPernaQuadro",
        ["Sem junta — sem colisão", "Sem tratamento — permitir colisão"],
        "Sem junta — sem colisão",
    )
    add_property(
        params, "App::PropertyLength", "LarguraPernaManual", "03 — Pernas",
        "Largura da perna. Zero copia a largura do quadro.", 0.0
    )
    add_property(
        params, "App::PropertyLength", "ProfundidadePernaManual", "03 — Pernas",
        "Profundidade da perna. Zero copia a largura do quadro.", 0.0
    )
    add_property(
        params, "App::PropertyLength", "PenetracaoPernaNoQuadro", "03 — Pernas",
        "Quanto as paredes da perna sobem para dentro do quadro. Zero usa automaticamente a espessura da chapa.", 0.0
    )

    # ------------------------------------------------------------------
    # 03B — União dentada dos quatro painéis das pernas.
    # ------------------------------------------------------------------
    migrando_para_v44 = add_property(
        params, "App::PropertyEnumeration", "UniaoPaineisPerna", "03B — Dentes das pernas",
        "Lisa mantém as quatro chapas retas. Dentada cria dentes verticais e rasgos complementares."
    )
    set_enum(
        params,
        "UniaoPaineisPerna",
        ["Lisa", "Dentada"],
        "Dentada",
    )
    add_property(
        params, "App::PropertyLength", "ComprimentoDentePerna", "03B — Dentes das pernas",
        "Altura de cada dente ao longo da perna.", 80.0
    )
    add_property(
        params, "App::PropertyLength", "EspacoDentesPerna", "03B — Dentes das pernas",
        "Espaço vertical livre entre dentes consecutivos.", 80.0
    )
    add_property(
        params, "App::PropertyLength", "ProfundidadeDentePerna", "03B — Dentes das pernas",
        "Quanto o dente entra na chapa receptora. Zero usa a espessura da parede.", 0.0
    )
    add_property(
        params, "App::PropertyLength", "MargemDentesPerna", "03B — Dentes das pernas",
        "Margem sem dentes nas extremidades superior e inferior do tubo.", 20.0
    )
    add_property(
        params, "App::PropertyLength", "FolgaDentesPerna", "03B — Dentes das pernas",
        "Folga adicional dos rasgos em relação aos dentes.", 0.15
    )

    # ------------------------------------------------------------------
    # 04 — Fechamento: primeiro escolhe tampas, depois o apoio superior.
    # ------------------------------------------------------------------
    add_property(
        params, "App::PropertyEnumeration", "TampasPerna", "04 — Fechamento da perna",
        "Escolha quais extremidades do tubo da perna serão fechadas."
    )
    set_enum(
        params,
        "TampasPerna",
        ["Nenhuma", "Somente superior", "Somente inferior", "Superior e inferior"],
        "Somente superior",
    )
    add_property(
        params, "App::PropertyEnumeration", "UniaoTampasPerna", "04 — Fechamento da perna",
        "Lisa apenas fecha a perna. Dentada cria dentes nas tampas e rasgos correspondentes nas quatro paredes."
    )
    set_enum(
        params,
        "UniaoTampasPerna",
        ["Lisa", "Dentada"],
        "Dentada",
    )
    add_property(
        params, "App::PropertyInteger", "QuantidadeDentesTampaPerna", "04 — Fechamento da perna",
        "Quantidade de dentes em cada lado da tampa superior/inferior.", 2
    )
    add_property(
        params, "App::PropertyLength", "LarguraDenteTampaPerna", "04 — Fechamento da perna",
        "Largura nominal dos dentes das tampas. A macro reduz automaticamente quando o lado for curto.", 30.0
    )
    add_property(
        params, "App::PropertyLength", "FolgaDentesTampaPerna", "04 — Fechamento da perna",
        "Folga dos rasgos que recebem os dentes das tampas.", 0.15
    )
    add_property(
        params, "App::PropertyLength", "EspessuraTampoPerna", "04 — Fechamento da perna",
        "Espessura da tampa. Zero usa a espessura da parede.", 0.0
    )
    add_property(
        params, "App::PropertyLength", "FolgaTampaInterna", "04 — Fechamento da perna",
        "Folga por lado para a tampa ficar dentro da cavidade da perna.", 0.20
    )
    add_property(
        params, "App::PropertyLength", "RebaixoTampaPerna", "04 — Fechamento da perna",
        "Recuo adicional da tampa em relação à extremidade da perna. Zero deixa a tampa encaixada rente, como a tampa inferior.", 0.0
    )
    add_property(
        params, "App::PropertyEnumeration", "ApoioSuperiorPerna", "04 — Fechamento da perna",
        "Disponível quando existe tampa superior."
    )
    set_enum(
        params,
        "ApoioSuperiorPerna",
        ["Somente tampa lisa", "Toco com chapas", "Tampa-costela dentada"],
        "Toco com chapas",
    )
    add_property(
        params, "App::PropertyBool", "RecortarPainelInferiorQuadro", "04 — Fechamento da perna",
        "Abre o painel inferior do quadro para receber o apoio da perna.", True
    )

    # ------------------------------------------------------------------
    # 04B — Fechamento inferior e nivelador.
    # ------------------------------------------------------------------
    add_property(
        params, "App::PropertyBool", "PrepararNivelador", "04B — Nivelador",
        "Garante tampa inferior e abre um furo central para instalar pé nivelador.", False
    )
    add_property(
        params, "App::PropertyLength", "DiametroFuroNivelador", "04B — Nivelador",
        "Diâmetro do furo passante central da tampa inferior.", 10.0
    )
    add_property(
        params, "App::PropertyBool", "CriarRebaixoNivelador", "04B — Nivelador",
        "Cria um rebaixo circular na face inferior da tampa para porca, bucha ou flange.", False
    )
    add_property(
        params, "App::PropertyLength", "DiametroRebaixoNivelador", "04B — Nivelador",
        "Diâmetro do rebaixo circular do nivelador.", 24.0
    )
    add_property(
        params, "App::PropertyLength", "ProfundidadeRebaixoNivelador", "04B — Nivelador",
        "Profundidade do rebaixo. Deve ser menor que a espessura da tampa.", 5.0
    )
    add_property(
        params, "App::PropertyBool", "BasePernaNoChao", "04B — Nivelador",
        "Mantém a face inferior da tampa/base exatamente no fim da linha da perna, definindo o nível do chão.", True
    )

    # Compatibilidade: conserva a propriedade antiga, mas a oculta.
    add_property(
        params, "App::PropertyEnumeration", "FixacaoSuperiorPerna", "Compatibilidade",
        "Propriedade antiga; use ApoioSuperiorPerna."
    )
    set_enum(
        params,
        "FixacaoSuperiorPerna",
        ["Sem fixação", "Toco com chapas"],
        "Toco com chapas",
    )
    try:
        params.setEditorMode("FixacaoSuperiorPerna", 2)
    except Exception:
        pass

    # ------------------------------------------------------------------
    # 05 — Toco / tampa-costela.
    # ------------------------------------------------------------------
    add_property(
        params, "App::PropertyInteger", "QuantidadeChapasToco", "05 — Apoio superior",
        "Quantidade de chapas empilhadas no toco.", 3
    )
    # Em documentos vindos da V4.3, atualiza apenas o antigo valor padrão 2.
    # Valores personalizados pelo usuário são preservados.
    if migrando_para_v44 and int(params.QuantidadeChapasToco) == 2:
        params.QuantidadeChapasToco = 3
    add_property(
        params, "App::PropertyLength", "EspessuraChapaToco", "05 — Apoio superior",
        "Espessura de cada chapa do toco. Zero usa EspessuraParede.", 0.0
    )
    add_property(
        params, "App::PropertyLength", "FolgaToco", "05 — Apoio superior",
        "Folga em cada lado do toco.", 0.50
    )
    add_property(
        params, "App::PropertyLength", "LarguraTocoManual", "05 — Apoio superior",
        "Largura manual. Zero calcula pela cavidade da perna.", 0.0
    )
    add_property(
        params, "App::PropertyLength", "ProfundidadeTocoManual", "05 — Apoio superior",
        "Profundidade manual. Zero calcula pela cavidade da perna.", 0.0
    )
    add_property(
        params, "App::PropertyEnumeration", "ApoioPainelInferiorNoPe", "05 — Apoio superior",
        "Define se o painel inferior horizontal fica livre ou descansa em um ombro sobre a perna."
    )
    set_enum(
        params,
        "ApoioPainelInferiorNoPe",
        ["Não apoiar — encaixe livre", "Apoiar no ombro"],
        "Não apoiar — encaixe livre",
    )
    add_property(
        params, "App::PropertyBool", "CriarOmbroApoio", "Compatibilidade",
        "Propriedade antiga; use ApoioPainelInferiorNoPe.", False
    )
    try:
        params.setEditorMode("CriarOmbroApoio", 2)
    except Exception:
        pass
    add_property(
        params, "App::PropertyLength", "EspessuraOmbroApoio", "05 — Apoio superior",
        "Espessura do ombro. Zero usa EspessuraParede.", 0.0
    )
    add_property(
        params, "App::PropertyLength", "FolgaOmbroApoio", "05 — Apoio superior",
        "Recuo por lado do ombro em relação ao contorno externo da perna.", 0.0
    )
    add_property(
        params, "App::PropertyEnumeration", "LadosDentadosTampaCostela", "05 — Apoio superior",
        "Automático usa um lado em perna intermediária e dois lados em perna de canto."
    )
    set_enum(
        params,
        "LadosDentadosTampaCostela",
        ["Automático", "1 lado interno", "2 lados internos"],
        "Automático",
    )
    add_property(
        params, "App::PropertyBool", "CriarCostelaConexaoT", "05 — Apoio superior",
        "Em pernas intermediárias, cria uma costela alinhada à perna para formar a conexão em T.", True
    )
    add_property(
        params, "App::PropertyBool", "CostelaTRespeitaToco", "05 — Apoio superior",
        "Limita o corpo da costela em T ao topo do toco, evitando colisão; o dente profundo usa os rasgos do toco.", True
    )
    add_property(
        params, "App::PropertyLength", "FolgaCostelaToco", "05 — Apoio superior",
        "Folga vertical entre o corpo da costela em T e o topo do toco.", 0.30
    )
    add_property(
        params, "App::PropertyBool", "DenteInferiorProfundo", "05 — Apoio superior",
        "Na costela da conexão em T, prolonga um dente para atravessar o painel inferior e entrar na tampa da perna.", True
    )
    add_property(
        params, "App::PropertyLength", "ProfundidadeDenteInferior", "05 — Apoio superior",
        "Profundidade total do dente inferior. Zero calcula até o interior da tampa.", 0.0
    )

    # ------------------------------------------------------------------
    # 06 — Costelas: usuário escolhe quantidade e método de montagem.
    # ------------------------------------------------------------------
    add_property(
        params, "App::PropertyBool", "CriarCostelas", "06 — Costelas internas",
        "Cria reforços internos automaticamente.", True
    )
    add_property(
        params, "App::PropertyLength", "VaoMaximoCostelas", "06 — Costelas internas",
        "Vão de referência. Ex.: 500 mm.", 500.0
    )
    add_property(
        params, "App::PropertyInteger", "NumeroCostelasPorSegmento", "06 — Costelas internas",
        "Quantidade manual por segmento. Zero distribui automaticamente.", 0
    )
    add_property(
        params, "App::PropertyLength", "EspessuraCostela", "06 — Costelas internas",
        "Espessura da placa da costela.", 15.0
    )
    add_property(
        params, "App::PropertyLength", "FolgaCostela", "06 — Costelas internas",
        "Folga ao redor da costela lisa.", 0.30
    )
    add_property(
        params, "App::PropertyLength", "LarguraCostelaManual", "06 — Costelas internas",
        "Largura manual. Zero ajusta à cavidade.", 0.0
    )
    add_property(
        params, "App::PropertyLength", "AlturaCostelaManual", "06 — Costelas internas",
        "Altura manual. Zero ajusta à cavidade.", 0.0
    )
    add_property(
        params, "App::PropertyEnumeration", "MontagemCostelas", "06 — Costelas internas",
        "Escolha como as costelas serão presas."
    )
    set_enum(
        params,
        "MontagemCostelas",
        ["Parafusadas", "Encaixadas", "Encaixadas + parafusadas"],
        "Encaixadas + parafusadas",
    )
    add_property(
        params, "App::PropertyEnumeration", "LadosDentadosCostela", "06 — Costelas internas",
        "Quantidade de bordas da costela que recebem dentes."
    )
    set_enum(
        params,
        "LadosDentadosCostela",
        ["2 lados opostos", "3 lados", "4 lados"],
        "3 lados",
    )

    # ------------------------------------------------------------------
    # 07 — Encaixes CNC: aparece apenas quando existe montagem por encaixe.
    # ------------------------------------------------------------------
    add_property(
        params, "App::PropertyInteger", "QuantidadeDentesPorLadoCostela", "07 — Encaixes CNC",
        "Quantidade de dentes em cada borda selecionada.", 2
    )
    add_property(
        params, "App::PropertyLength", "LarguraDenteCostela", "07 — Encaixes CNC",
        "Largura de cada dente ao longo da borda.", 20.0
    )
    add_property(
        params, "App::PropertyLength", "ProfundidadeDenteCostela", "07 — Encaixes CNC",
        "Quanto o dente entra na parede. Zero usa EspessuraParede + FolgaCostela.", 0.0
    )
    add_property(
        params, "App::PropertyLength", "FolgaEncaixeCostela", "07 — Encaixes CNC",
        "Folga adicional dos rasgos em relação aos dentes.", 0.15
    )
    add_property(
        params, "App::PropertyBool", "GerarRasgosReais", "07 — Encaixes CNC",
        "Subtrai todos os rasgos fêmea correspondentes aos dentes: costelas, quadro, pernas, tampas e conexão T.", True
    )
    add_property(
        params, "App::PropertyEnumeration", "AlivioCantosRasgos", "07 — Encaixes CNC",
        "Aplica osso de cão integrado nos rasgos do esqueleto/conexão T e nos rasgos das pernas; não cria furos nas pontas dos dentes do quadro."
    )
    set_enum(
        params,
        "AlivioCantosRasgos",
        ["Desativado", "Osso de cão integrado"],
        "Osso de cão integrado",
    )
    add_property(
        params, "App::PropertyEnumeration", "OrientacaoAlivioCNC", "07 — Encaixes CNC",
        "Automática usa os eixos locais do rasgo e coloca o alívio deitado no lado curto. Diagonal mantém o dogbone clássico."
    )
    set_enum(
        params,
        "OrientacaoAlivioCNC",
        ["Automática pelo rasgo", "Diagonal clássica"],
        "Automática pelo rasgo",
    )
    add_property(
        params, "App::PropertyLength", "DiametroFresaRasgos", "07 — Encaixes CNC",
        "Diâmetro da fresa usada nos rasgos; define o tamanho do osso de cão.", 6.0
    )
    add_property(
        params, "App::PropertyLength", "FolgaExtraOssoDeCao", "07 — Encaixes CNC",
        "Aumento radial opcional além do raio nominal da fresa.", 0.10
    )
    add_property(
        params, "App::PropertyBool", "MigracaoV45Aplicada", "Compatibilidade",
        "Controle interno para aplicar os padrões corretivos da V4.5 uma única vez.", False
    )
    if not bool(params.MigracaoV45Aplicada):
        # A V4.5 nasce com o conjunto completo visível: macho + fêmea.
        params.GerarRasgosReais = True
        params.AlivioCantosRasgos = "Osso de cão integrado"
        params.UniaoPaineisPerna = "Dentada"
        params.ApoioPainelInferiorNoPe = "Não apoiar — encaixe livre"
        if int(params.QuantidadeChapasToco) < 3:
            params.QuantidadeChapasToco = 3
        params.MigracaoV45Aplicada = True
    try:
        params.setEditorMode("MigracaoV45Aplicada", 2)
    except Exception:
        pass
    add_property(
        params, "App::PropertyBool", "MigracaoV46Aplicada", "Compatibilidade",
        "Controle interno dos padrões corretivos da V4.7.", False
    )
    if not bool(params.MigracaoV46Aplicada):
        params.UniaoTampasPerna = "Dentada"
        params.OrientacaoAlivioCNC = "Automática pelo rasgo"
        params.GerarRasgosReais = True
        params.MigracaoV46Aplicada = True
    try:
        params.setEditorMode("MigracaoV46Aplicada", 2)
    except Exception:
        pass
    add_property(
        params, "App::PropertyLength", "DiametroFuroCostela", "07 — Encaixes CNC",
        "Diâmetro de referência para costelas parafusadas.", 3.0
    )
    add_property(
        params, "App::PropertyInteger", "QuantidadeFurosCostela", "07 — Encaixes CNC",
        "Quantidade de furos reais por face de contato e por costela.", 2
    )
    add_property(
        params, "App::PropertyBool", "GerarFurosReaisCostelas", "07 — Encaixes CNC",
        "Abre furos passantes reais nas quatro chapas que encostam em cada costela.", True
    )

    add_property(
        params, "App::PropertyBool", "GerarFurosDentesQuadro", "07B — Furos nos dentes",
        "Abre furos reais no centro dos dentes macho das paredes do quadro.", True
    )
    add_property(
        params, "App::PropertyBool", "GerarFurosDentesPernas", "07B — Furos nos dentes",
        "Abre furos reais nos dentes macho dos painéis frontal e traseiro das pernas.", True
    )
    add_property(
        params, "App::PropertyBool", "GerarFurosDentesTampas", "07B — Furos nos dentes",
        "Abre furos reais nos dentes macho das tampas superior e inferior das pernas.", True
    )
    add_property(
        params, "App::PropertyBool", "GerarFurosDentesCostelas", "07B — Furos nos dentes",
        "Abre furos reais nos dentes macho das costelas normais, de conexão T e dos abraços do toco local.", True
    )
    add_property(
        params, "App::PropertyLength", "DiametroFuroDente", "07B — Furos nos dentes",
        "Diâmetro dos furos de montagem feitos nos dentes.", 3.0
    )
    add_property(
        params, "App::PropertyInteger", "QuantidadeFurosPorDente", "07B — Furos nos dentes",
        "Quantidade de furos distribuídos em cada dente macho.", 1
    )
    add_property(
        params, "App::PropertyLength", "RecuoFuroDente", "07B — Furos nos dentes",
        "Margem nas extremidades do dente. Zero usa metade da espessura da chapa.", 0.0
    )
    add_property(
        params, "App::PropertyBool", "FurarPecasReceptorasDentes", "07B — Furos nos dentes",
        "Fura também as peças fêmea: topo/fundo do quadro e laterais das pernas, alinhadas aos dentes.", True
    )

    add_property(
        params, "App::PropertyBool", "MigracaoV411Aplicada", "Compatibilidade",
        "Controle interno dos padrões da V4.11.", False
    )
    if not bool(params.MigracaoV411Aplicada):
        params.BasePernaNoChao = True
        params.CostelaTRespeitaToco = True
        params.FolgaCostelaToco = 0.30
        params.FurarPecasReceptorasDentes = True
        params.MigracaoV411Aplicada = True
    try:
        params.setEditorMode("MigracaoV411Aplicada", 2)
    except Exception:
        pass

    # ------------------------------------------------------------------
    # 08 — Visualização.
    # ------------------------------------------------------------------
    add_property(
        params, "App::PropertyBool", "ExibirOrigens", "08 — Visualização",
        "Mantém visíveis as linhas usadas como esqueleto.", True
    )
    add_property(
        params, "App::PropertyBool", "ExibirSketchesGerados", "08 — Visualização",
        "Compatibilidade: exibe Sketches internos quando existirem.", False
    )
    add_property(
        params, "App::PropertyBool", "ExibirMarcadoresFuro", "08 — Visualização",
        "Exibe guias visuais opcionais. Os furos reais não dependem desta opção.", False
    )

    add_property(
        params, "App::PropertyBool", "MigracaoV48Aplicada", "Compatibilidade",
        "Controle interno dos padrões corretivos da V4.8.", False
    )
    if not bool(params.MigracaoV48Aplicada):
        if str(params.MontagemCostelas) == "Encaixadas":
            params.MontagemCostelas = "Encaixadas + parafusadas"
        params.ExibirMarcadoresFuro = True
        params.MigracaoV48Aplicada = True
    try:
        params.setEditorMode("MigracaoV48Aplicada", 2)
    except Exception:
        pass

    add_property(
        params, "App::PropertyBool", "MigracaoV49Aplicada", "Compatibilidade",
        "Controle interno da migração para furos reais nas costelas e nos dentes.", False
    )
    if not bool(params.MigracaoV49Aplicada):
        params.GerarFurosReaisCostelas = True
        params.ExibirMarcadoresFuro = False
        if int(params.QuantidadeFurosCostela) < 2:
            params.QuantidadeFurosCostela = 2
        if str(params.MontagemCostelas) == "Encaixadas":
            params.MontagemCostelas = "Encaixadas + parafusadas"
        params.MigracaoV49Aplicada = True
    try:
        params.setEditorMode("MigracaoV49Aplicada", 2)
    except Exception:
        pass

    add_property(
        params, "App::PropertyBool", "MigracaoV410Aplicada", "Compatibilidade",
        "Controle interno da migração para furos nos dentes e fechamento inferior.", False
    )
    if not bool(params.MigracaoV410Aplicada):
        params.GerarFurosDentesQuadro = True
        params.GerarFurosDentesPernas = True
        params.GerarFurosDentesTampas = True
        params.ExibirMarcadoresFuro = False
        # Atualiza apenas o antigo padrão; escolhas explícitas diferentes são preservadas.
        if str(params.TampasPerna) == "Somente superior":
            params.TampasPerna = "Superior e inferior"
        params.MigracaoV410Aplicada = True
    try:
        params.setEditorMode("MigracaoV410Aplicada", 2)
    except Exception:
        pass

    add_property(
        params, "App::PropertyString", "FluxoDeUso", "00 — COMO USAR",
        "Sequência resumida de configuração."
    )
    params.FluxoDeUso = (
        "1) selecione linhas; 2) configure quadro e união lisa/dentada; "
        "3) configure dimensões e dentes das pernas; 4) escolha tampas, toco e apoio livre/ombro; "
        "5) escolha parafusar ou encaixar costelas; 6) execute novamente a macro."
    )
    add_property(
        params, "App::PropertyString", "RegraDimensional", "00 — COMO USAR",
        "Regra dimensional principal."
    )
    params.RegraDimensional = (
        "O contorno fechado é o limite externo. O quadro e as pernas crescem para dentro."
    )
    add_property(
        params, "App::PropertyString", "ComoAtualizar", "00 — COMO USAR",
        "Instrução de atualização."
    )
    params.ComoAtualizar = (
        "Altere as opções e execute novamente Gerador_Estrutura_Esqueleto_v4_13_TAMPAS_SIMETRICAS.FCMacro."
    )
    add_property(
        params, "App::PropertyString", "AvisoGeometria", "00 — COMO USAR",
        "Orientação para evitar falhas do OpenCascade."
    )
    params.AvisoGeometria = (
        "Cada painel, ombro, tampa e costela é um Part::Feature separado. Não funda a mesa inteira: "
        "exporte e usine as peças individualmente."
    )

    try:
        params.setEditorMode("CriarOmbroApoio", 2)
    except Exception:
        pass
    set_read_only(params, ("FluxoDeUso", "RegraDimensional", "ComoAtualizar", "AvisoGeometria"))
    return params


def upper_cap_enabled(p):
    return p["leg_caps"] in ("Somente superior", "Superior e inferior")


def lower_cap_enabled(p):
    return (
        p["leg_caps"] in ("Somente inferior", "Superior e inferior")
        or p.get("prepare_leveler", False)
    )


def leg_cap_joint_enabled(p):
    return p.get("leg_cap_joint") == "Dentada"


def leg_no_joint(p):
    return p["leg_connection"].startswith("Sem junta")


def toco_enabled(p):
    return upper_cap_enabled(p) and p["upper_support"] == "Toco com chapas"


def frame_joint_enabled(p):
    return p.get("frame_joint", "Lisa") == "Dentada"


def frame_tooth_depth(p):
    depth = p.get("frame_tooth_depth", 0.0)
    return depth if depth > TOL else p["wall"]


def leg_joint_enabled(p):
    return p.get("leg_joint", "Lisa") == "Dentada"


def leg_tooth_depth(p):
    depth = p.get("leg_tooth_depth", 0.0)
    return depth if depth > TOL else p["wall"]


def support_shoulder_enabled(p):
    return (
        leg_no_joint(p)
        and upper_cap_enabled(p)
        and p.get("lower_panel_support", "Não apoiar — encaixe livre") == "Apoiar no ombro"
        and p["upper_support"] in ("Toco com chapas", "Tampa-costela dentada")
    )


def shoulder_thickness(p):
    value = p.get("support_shoulder_thickness", 0.0)
    return value if value > TOL else p["wall"]


def shoulder_dimensions(p):
    leg_w, leg_d = leg_dimensions(p)
    clearance = p.get("support_shoulder_clearance", 0.0)
    width = leg_w - 2.0 * clearance
    depth = leg_d - 2.0 * clearance
    if width <= TOL or depth <= TOL:
        raise ValueError("A folga deixa o ombro de apoio sem dimensão útil.")
    return width, depth, clearance, clearance


def tampa_costela_enabled(p):
    return upper_cap_enabled(p) and p["upper_support"] == "Tampa-costela dentada"


def upper_support_occupies_frame(p):
    return leg_no_joint(p) and upper_cap_enabled(p) and p["upper_support"] in (
        "Toco com chapas", "Tampa-costela dentada"
    )


def costela_encaixe_enabled(p):
    return p["rib_mount"] in ("Encaixadas", "Encaixadas + parafusadas")


def costela_parafuso_enabled(p):
    return p["rib_mount"] in ("Parafusadas", "Encaixadas + parafusadas")


def leg_dimensions(p):
    width = p["leg_width_manual"] if p["leg_width_manual"] > TOL else p["profile_width"]
    depth = p["leg_depth_manual"] if p["leg_depth_manual"] > TOL else p["profile_width"]
    return width, depth


def cap_thickness(p):
    return p["cap_thickness"] if p["cap_thickness"] > TOL else p["wall"]


def cap_recess(p):
    """
    Recuo adicional da tampa a partir da extremidade.

    Zero mantém a tampa encaixada rente:
    - tampa superior: ocupa a primeira espessura interna da perna;
    - tampa inferior: ocupa a última espessura junto ao piso.
    """
    return max(0.0, p.get("cap_recess", 0.0))


def lower_cap_z(p, total_length, thickness):
    """No modo piso, a face inferior da tampa coincide com o final da linha da perna."""
    if p.get("base_leg_on_floor", True):
        return total_length - thickness
    return total_length - thickness - cap_recess(p)


def connection_rib_bottom_limit(p):
    """Limite +Z do corpo da costela T antes do volume ocupado pelo toco."""
    regular = p["profile_height"] - p["wall"] - p["rib_clearance"]
    if not p.get("t_rib_respects_toco", True):
        return regular
    if toco_enabled(p):
        stack = p["toco_plate_count"] * toco_plate_thickness(p)
        shoulder_t = shoulder_thickness(p) if support_shoulder_enabled(p) else 0.0

        # Posição local da face superior da tampa:
        # fundo do quadro - penetração da perna + ombro opcional + rebaixo manual.
        upper_cap_top = (
            p["profile_height"]
            - leg_frame_penetration(p)
            + shoulder_t
            + cap_recess(p)
        )
        minimum = (
            p["wall"]
            + p["rib_clearance"]
            + max(p["rib_tab_width"], p["wall"])
        )
        return max(
            minimum,
            upper_cap_top
            - stack
            - p.get("t_rib_toco_clearance", 0.30),
        )
    return regular


def leg_frame_penetration(p):
    """Penetração das paredes da perna dentro do quadro. Zero = uma espessura de chapa."""
    value = p.get("leg_frame_penetration", 0.0)
    return value if value > TOL else p["wall"]


def internal_cap_dimensions(p):
    leg_w, leg_d = leg_dimensions(p)
    clearance = p.get("cap_internal_clearance", 0.20)
    width = leg_w - 2.0 * p["wall"] - 2.0 * clearance
    depth = leg_d - 2.0 * p["wall"] - 2.0 * clearance
    if width <= TOL or depth <= TOL:
        raise ValueError("A folga deixa a tampa interna sem dimensão útil.")
    return width, depth, p["wall"] + clearance, p["wall"] + clearance


def support_opening_dimensions(p):
    if toco_enabled(p):
        return toco_dimensions(p)
    if tampa_costela_enabled(p):
        width, depth, _x0, _y0 = internal_cap_dimensions(p)
        return width, depth
    return (0.0, 0.0)


def deep_lower_tooth_depth(p):
    if p.get("deep_lower_tooth_depth", 0.0) > TOL:
        return p["deep_lower_tooth_depth"]
    extra = cap_thickness(p)
    if support_shoulder_enabled(p):
        extra += shoulder_thickness(p)
    return tooth_depth(p) + extra


def toco_plate_thickness(p):
    return p["toco_plate_thickness"] if p["toco_plate_thickness"] > TOL else p["wall"]


def toco_dimensions(p):
    leg_w, leg_d = leg_dimensions(p)
    auto_w = leg_w - 2.0 * p["wall"] - 2.0 * p["toco_clearance"]
    auto_d = leg_d - 2.0 * p["wall"] - 2.0 * p["toco_clearance"]
    width = p["toco_width_manual"] if p["toco_width_manual"] > TOL else auto_w
    depth = p["toco_depth_manual"] if p["toco_depth_manual"] > TOL else auto_d
    return width, depth


def tooth_depth(p):
    return p["rib_tooth_depth"] if p["rib_tooth_depth"] > TOL else p["wall"] + p["rib_clearance"]


def set_visible(params, names, visible):
    for name in names:
        try:
            params.setEditorMode(name, 0 if visible else 2)
        except Exception:
            pass


def update_editor_modes(params):
    cap_mode = str(params.TampasPerna)
    upper = cap_mode in ("Somente superior", "Superior e inferior")
    lower = cap_mode in ("Somente inferior", "Superior e inferior") or bool(params.PrepararNivelador)
    support = str(params.ApoioSuperiorPerna)
    create_ribs = bool(params.CriarCostelas)
    rib_mount = str(params.MontagemCostelas)
    encaixe = rib_mount in ("Encaixadas", "Encaixadas + parafusadas")
    parafuso = rib_mount in ("Parafusadas", "Encaixadas + parafusadas")
    frame_teeth = str(params.UniaoPaineisQuadro) == "Dentada"
    leg_teeth = str(params.UniaoPaineisPerna) == "Dentada"
    lower_support = str(params.ApoioPainelInferiorNoPe)

    set_visible(params, (
        "ComprimentoDenteQuadro", "EspacoDentesQuadro",
        "ProfundidadeDenteQuadro", "MargemDentesQuadro",
        "FolgaDentesQuadro",
    ), frame_teeth)
    set_visible(params, (
        "ComprimentoDentePerna", "EspacoDentesPerna",
        "ProfundidadeDentePerna", "MargemDentesPerna",
        "FolgaDentesPerna",
    ), leg_teeth)

    cap_exists = cap_mode != "Nenhuma"
    cap_joint = str(params.UniaoTampasPerna) == "Dentada"
    set_visible(params, ("UniaoTampasPerna", "RebaixoTampaPerna"), cap_exists)
    set_visible(params, (
        "QuantidadeDentesTampaPerna", "LarguraDenteTampaPerna",
        "FolgaDentesTampaPerna",
    ), cap_exists and cap_joint)

    set_visible(params, ("ApoioSuperiorPerna", "RecortarPainelInferiorQuadro"), upper)
    set_visible(params, (
        "QuantidadeChapasToco", "EspessuraChapaToco", "FolgaToco",
        "LarguraTocoManual", "ProfundidadeTocoManual"
    ), upper and support == "Toco com chapas")
    set_visible(params, ("ApoioPainelInferiorNoPe",), upper and support in ("Toco com chapas", "Tampa-costela dentada"))
    set_visible(params, (
        "EspessuraOmbroApoio", "FolgaOmbroApoio"
    ), upper and support in ("Toco com chapas", "Tampa-costela dentada") and lower_support == "Apoiar no ombro")
    set_visible(params, ("LadosDentadosTampaCostela",), upper and support == "Tampa-costela dentada")
    set_visible(params, ("CriarCostelaConexaoT",), upper)
    set_visible(params, ("CostelaTRespeitaToco", "FolgaCostelaToco"), upper and bool(params.CriarCostelaConexaoT))
    set_visible(params, ("DenteInferiorProfundo",), upper and bool(params.CriarCostelaConexaoT))
    set_visible(params, ("ProfundidadeDenteInferior",), upper and bool(params.CriarCostelaConexaoT) and bool(params.DenteInferiorProfundo))

    set_visible(params, (
        "VaoMaximoCostelas", "NumeroCostelasPorSegmento", "EspessuraCostela",
        "FolgaCostela", "LarguraCostelaManual", "AlturaCostelaManual",
        "MontagemCostelas"
    ), create_ribs)
    set_visible(params, ("LadosDentadosCostela",), create_ribs and encaixe)
    set_visible(params, (
        "QuantidadeDentesPorLadoCostela", "LarguraDenteCostela",
        "ProfundidadeDenteCostela", "FolgaEncaixeCostela", "GerarRasgosReais"
    ), create_ribs and encaixe)

    any_slot = frame_teeth or leg_teeth or (create_ribs and encaixe and bool(params.GerarRasgosReais))
    set_visible(params, ("AlivioCantosRasgos",), any_slot)
    dogbone_visible = (
        any_slot and str(params.AlivioCantosRasgos) == "Osso de cão integrado"
    )
    set_visible(params, ("DiametroFresaRasgos", "FolgaExtraOssoDeCao", "OrientacaoAlivioCNC"), dogbone_visible)
    set_visible(params, ("DiametroFuroCostela", "QuantidadeFurosCostela", "GerarFurosReaisCostelas"), create_ribs and parafuso)

    set_visible(params, ("PrepararNivelador",), True)
    set_visible(params, (
        "DiametroFuroNivelador", "CriarRebaixoNivelador"
    ), bool(params.PrepararNivelador))
    set_visible(params, (
        "DiametroRebaixoNivelador", "ProfundidadeRebaixoNivelador"
    ), bool(params.PrepararNivelador) and bool(params.CriarRebaixoNivelador))

    set_visible(params, ("GerarFurosDentesQuadro",), frame_teeth)
    set_visible(params, ("GerarFurosDentesPernas",), leg_teeth)
    set_visible(params, ("GerarFurosDentesTampas",), lower or upper)
    set_visible(
        params, ("GerarFurosDentesCostelas",),
        create_ribs and encaixe
    )
    any_tooth_hole = (
        (frame_teeth and bool(params.GerarFurosDentesQuadro))
        or (leg_teeth and bool(params.GerarFurosDentesPernas))
        or ((lower or upper) and bool(params.GerarFurosDentesTampas))
        or (create_ribs and encaixe and bool(params.GerarFurosDentesCostelas))
    )
    set_visible(params, (
        "DiametroFuroDente", "QuantidadeFurosPorDente", "RecuoFuroDente"
    ), any_tooth_hole)


def read_parameters(params):
    update_editor_modes(params)
    mode_map = {
        "Somente quadro fechado": "Contorno externo planar",
        "Somente linhas 3D": "Rede 3D por eixos",
    }
    connection_map = {"Extremidades retas": "Sem aparar"}
    corner_map = {"Centralizar na linha": "Linha no centro do perfil"}

    raw_mode = str(params.ModoInterpretacao)
    raw_connection = str(params.TipoConexao)
    raw_corner = str(params.ModoPernasCanto)

    data = {
        "mode": mode_map.get(raw_mode, raw_mode),
        "connection": connection_map.get(raw_connection, raw_connection),
        "height_direction": str(params.DirecaoAlturaPlanar),
        "corner_legs": corner_map.get(raw_corner, raw_corner),
        "leg_connection": str(params.ConexaoPernaQuadro),
        "leg_caps": str(params.TampasPerna),
        "leg_cap_joint": str(params.UniaoTampasPerna),
        "leg_cap_tooth_count": int(params.QuantidadeDentesTampaPerna),
        "leg_cap_tooth_width": qvalue(params, "LarguraDenteTampaPerna"),
        "leg_cap_tooth_clearance": qvalue(params, "FolgaDentesTampaPerna"),
        "upper_support": str(params.ApoioSuperiorPerna),
        "trim_frame_lower": bool(params.RecortarPainelInferiorQuadro),
        "attach_tolerance": qvalue(params, "ToleranciaConexao"),
        "profile_width": qvalue(params, "LarguraPerfil"),
        "profile_height": qvalue(params, "AlturaPerfil"),
        "wall": qvalue(params, "EspessuraParede"),
        "normal_offset": qvalue(params, "DeslocamentoNormal"),
        "legacy_z": qvalue(params, "ElevacaoZ"),
        "frame_joint": str(params.UniaoPaineisQuadro),
        "frame_tooth_length": qvalue(params, "ComprimentoDenteQuadro"),
        "frame_tooth_gap": qvalue(params, "EspacoDentesQuadro"),
        "frame_tooth_depth": qvalue(params, "ProfundidadeDenteQuadro"),
        "frame_tooth_margin": qvalue(params, "MargemDentesQuadro"),
        "frame_tooth_clearance": qvalue(params, "FolgaDentesQuadro"),
        "leg_joint": str(params.UniaoPaineisPerna),
        "leg_tooth_length": qvalue(params, "ComprimentoDentePerna"),
        "leg_tooth_gap": qvalue(params, "EspacoDentesPerna"),
        "leg_tooth_depth": qvalue(params, "ProfundidadeDentePerna"),
        "leg_tooth_margin": qvalue(params, "MargemDentesPerna"),
        "leg_tooth_clearance": qvalue(params, "FolgaDentesPerna"),
        "leg_width_manual": qvalue(params, "LarguraPernaManual"),
        "leg_depth_manual": qvalue(params, "ProfundidadePernaManual"),
        "leg_frame_penetration": qvalue(params, "PenetracaoPernaNoQuadro"),
        "cap_thickness": qvalue(params, "EspessuraTampoPerna"),
        "cap_internal_clearance": qvalue(params, "FolgaTampaInterna"),
        "cap_recess": qvalue(params, "RebaixoTampaPerna"),
        "prepare_leveler": bool(params.PrepararNivelador),
        "leveler_hole_diameter": qvalue(params, "DiametroFuroNivelador"),
        "leveler_counterbore": bool(params.CriarRebaixoNivelador),
        "leveler_counterbore_diameter": qvalue(params, "DiametroRebaixoNivelador"),
        "leveler_counterbore_depth": qvalue(params, "ProfundidadeRebaixoNivelador"),
        "base_leg_on_floor": bool(params.BasePernaNoChao),
        "toco_plate_count": int(params.QuantidadeChapasToco),
        "toco_plate_thickness": qvalue(params, "EspessuraChapaToco"),
        "toco_clearance": qvalue(params, "FolgaToco"),
        "toco_width_manual": qvalue(params, "LarguraTocoManual"),
        "toco_depth_manual": qvalue(params, "ProfundidadeTocoManual"),
        "lower_panel_support": str(params.ApoioPainelInferiorNoPe),
        "create_support_shoulder": str(params.ApoioPainelInferiorNoPe) == "Apoiar no ombro",
        "support_shoulder_thickness": qvalue(params, "EspessuraOmbroApoio"),
        "support_shoulder_clearance": qvalue(params, "FolgaOmbroApoio"),
        "cap_rib_sides": str(params.LadosDentadosTampaCostela),
        "create_t_connection_rib": bool(params.CriarCostelaConexaoT),
        "t_rib_respects_toco": bool(params.CostelaTRespeitaToco),
        "t_rib_toco_clearance": qvalue(params, "FolgaCostelaToco"),
        "deep_lower_tooth": bool(params.DenteInferiorProfundo),
        "deep_lower_tooth_depth": qvalue(params, "ProfundidadeDenteInferior"),
        "create_ribs": bool(params.CriarCostelas),
        "rib_max_span": qvalue(params, "VaoMaximoCostelas"),
        "rib_count_manual": int(params.NumeroCostelasPorSegmento),
        "rib_thickness": qvalue(params, "EspessuraCostela"),
        "rib_clearance": qvalue(params, "FolgaCostela"),
        "rib_width_manual": qvalue(params, "LarguraCostelaManual"),
        "rib_height_manual": qvalue(params, "AlturaCostelaManual"),
        "rib_mount": str(params.MontagemCostelas),
        "rib_tab_sides": str(params.LadosDentadosCostela),
        "rib_tab_count": int(params.QuantidadeDentesPorLadoCostela),
        "rib_tab_width": qvalue(params, "LarguraDenteCostela"),
        "rib_tooth_depth": qvalue(params, "ProfundidadeDenteCostela"),
        "rib_slot_clearance": qvalue(params, "FolgaEncaixeCostela"),
        "real_slots": bool(params.GerarRasgosReais),
        "slot_corner_relief": str(params.AlivioCantosRasgos),
        "slot_tool_diameter": qvalue(params, "DiametroFresaRasgos"),
        "dogbone_extra_clearance": qvalue(params, "FolgaExtraOssoDeCao"),
        "dogbone_orientation": str(params.OrientacaoAlivioCNC),
        "rib_hole_diameter": qvalue(params, "DiametroFuroCostela"),
        "rib_hole_count": int(params.QuantidadeFurosCostela),
        "real_rib_holes": bool(params.GerarFurosReaisCostelas),
        "tooth_holes_frame": bool(params.GerarFurosDentesQuadro),
        "tooth_holes_leg": bool(params.GerarFurosDentesPernas),
        "tooth_holes_cap": bool(params.GerarFurosDentesTampas),
        "tooth_holes_rib": bool(params.GerarFurosDentesCostelas),
        "tooth_hole_diameter": qvalue(params, "DiametroFuroDente"),
        "tooth_hole_count": int(params.QuantidadeFurosPorDente),
        "tooth_hole_edge": qvalue(params, "RecuoFuroDente"),
        "tooth_holes_receivers": bool(params.FurarPecasReceptorasDentes),
        "show_sources": bool(params.ExibirOrigens),
        "show_generated_sketches": bool(params.ExibirSketchesGerados),
        "show_hole_markers": bool(params.ExibirMarcadoresFuro),
    }
    validate_parameters(data)
    return data


def validate_parameters(p):
    if p["attach_tolerance"] < 0:
        raise ValueError("ToleranciaConexao não pode ser negativa.")
    if p["leg_frame_penetration"] < 0:
        raise ValueError("PenetracaoPernaNoQuadro não pode ser negativa.")
    if p["profile_width"] <= 0 or p["profile_height"] <= 0 or p["wall"] <= 0:
        raise ValueError("As dimensões do quadro devem ser maiores que zero.")
    if 2.0 * p["wall"] >= p["profile_width"]:
        raise ValueError("EspessuraParede deve ser menor que metade de LarguraPerfil.")
    if 2.0 * p["wall"] >= p["profile_height"]:
        raise ValueError("EspessuraParede deve ser menor que metade de AlturaPerfil.")
    if leg_frame_penetration(p) >= p["profile_height"] - TOL:
        raise ValueError("PenetracaoPernaNoQuadro deve ser menor que AlturaPerfil.")

    if frame_joint_enabled(p):
        if p["frame_tooth_length"] <= 0:
            raise ValueError("ComprimentoDenteQuadro deve ser maior que zero.")
        if p["frame_tooth_gap"] < 0:
            raise ValueError("EspacoDentesQuadro não pode ser negativo.")
        if p["frame_tooth_margin"] < 0 or p["frame_tooth_clearance"] < 0:
            raise ValueError("Margem e folga dos dentes do quadro não podem ser negativas.")
        depth = frame_tooth_depth(p)
        if depth <= 0 or depth > p["wall"] + TOL:
            raise ValueError("ProfundidadeDenteQuadro deve ficar entre zero e a espessura da chapa.")

    if leg_joint_enabled(p):
        if p["leg_tooth_length"] <= 0:
            raise ValueError("ComprimentoDentePerna deve ser maior que zero.")
        if p["leg_tooth_gap"] < 0:
            raise ValueError("EspacoDentesPerna não pode ser negativo.")
        if p["leg_tooth_margin"] < 0 or p["leg_tooth_clearance"] < 0:
            raise ValueError("Margem e folga dos dentes da perna não podem ser negativas.")
        depth = leg_tooth_depth(p)
        if depth <= 0 or depth > p["wall"] + TOL:
            raise ValueError("ProfundidadeDentePerna deve ficar entre zero e a espessura da chapa.")

    if dogbone_enabled(p):
        if p["slot_tool_diameter"] <= 0:
            raise ValueError("DiametroFresaRasgos deve ser maior que zero.")
        if p["dogbone_extra_clearance"] < 0:
            raise ValueError("FolgaExtraOssoDeCao não pode ser negativa.")

    leg_w, leg_d = leg_dimensions(p)
    if leg_w <= 0 or leg_d <= 0:
        raise ValueError("As dimensões da perna devem ser maiores que zero.")
    if 2.0 * p["wall"] >= leg_w or 2.0 * p["wall"] >= leg_d:
        raise ValueError("A espessura da parede não cabe na seção da perna.")

    if p["cap_thickness"] < 0:
        raise ValueError("EspessuraTampoPerna não pode ser negativa.")
    if p["leg_cap_joint"] == "Dentada":
        if p["leg_cap_tooth_count"] < 1:
            raise ValueError("QuantidadeDentesTampaPerna deve ser pelo menos 1.")
        if p["leg_cap_tooth_width"] <= 0:
            raise ValueError("LarguraDenteTampaPerna deve ser maior que zero.")
        if p["leg_cap_tooth_clearance"] < 0:
            raise ValueError("FolgaDentesTampaPerna não pode ser negativa.")
    if p["toco_plate_count"] < 1:
        raise ValueError("QuantidadeChapasToco deve ser pelo menos 1.")
    if p["toco_plate_thickness"] < 0 or p["toco_clearance"] < 0:
        raise ValueError("EspessuraChapaToco e FolgaToco não podem ser negativas.")
    if p["toco_width_manual"] < 0 or p["toco_depth_manual"] < 0:
        raise ValueError("As dimensões manuais do toco não podem ser negativas.")
    if p["cap_internal_clearance"] < 0:
        raise ValueError("FolgaTampaInterna não pode ser negativa.")
    if p["cap_recess"] < 0:
        raise ValueError("RebaixoTampaPerna não pode ser negativo.")
    if p.get("prepare_leveler", False):
        if p["leveler_hole_diameter"] <= 0:
            raise ValueError("DiametroFuroNivelador deve ser maior que zero.")
        cap_w, cap_d, _cx, _cy = internal_cap_dimensions(p)
        if p["leveler_hole_diameter"] >= min(cap_w, cap_d):
            raise ValueError("DiametroFuroNivelador é grande demais para a tampa inferior.")
        if p["leveler_counterbore"]:
            if p["leveler_counterbore_diameter"] <= p["leveler_hole_diameter"]:
                raise ValueError("DiametroRebaixoNivelador deve ser maior que o furo passante.")
            if p["leveler_counterbore_depth"] <= 0 or p["leveler_counterbore_depth"] >= cap_thickness(p):
                raise ValueError("ProfundidadeRebaixoNivelador deve ficar entre zero e a espessura da tampa.")
    if p["support_shoulder_thickness"] < 0 or p["support_shoulder_clearance"] < 0:
        raise ValueError("Espessura e folga do ombro de apoio não podem ser negativas.")
    if support_shoulder_enabled(p):
        shoulder_w, shoulder_d, _sx, _sy = shoulder_dimensions(p)
        if shoulder_w <= 0 or shoulder_d <= 0:
            raise ValueError("O ombro de apoio ficou sem dimensão útil.")
        if shoulder_thickness(p) <= 0:
            raise ValueError("A espessura do ombro de apoio deve ser maior que zero.")
    if p["deep_lower_tooth_depth"] < 0:
        raise ValueError("ProfundidadeDenteInferior não pode ser negativa.")

    if toco_enabled(p):
        cap_t = cap_thickness(p)
        plate_t = toco_plate_thickness(p)
        stack = cap_t + p["toco_plate_count"] * plate_t
        if stack >= p["profile_height"] - p["wall"]:
            raise ValueError("Tampa + chapas do toco ocupam altura demais dentro do quadro.")
        toco_w, toco_d = toco_dimensions(p)
        if toco_w <= 0 or toco_d <= 0:
            raise ValueError("A folga deixa o toco com dimensão inválida.")

    if p["rib_count_manual"] < 0 or p["rib_clearance"] < 0:
        raise ValueError("Quantidade e folga das costelas não podem ser negativas.")
    if p["create_ribs"]:
        if p["rib_count_manual"] == 0 and p["rib_max_span"] <= 0:
            raise ValueError("VaoMaximoCostelas deve ser maior que zero.")
        if p["rib_thickness"] <= 0:
            raise ValueError("EspessuraCostela deve ser maior que zero.")
        if p["rib_width_manual"] < 0 or p["rib_height_manual"] < 0:
            raise ValueError("Dimensões manuais da costela não podem ser negativas.")

    if costela_encaixe_enabled(p):
        if p["rib_tab_count"] < 1:
            raise ValueError("QuantidadeDentesPorLadoCostela deve ser pelo menos 1.")
        if p["rib_tab_width"] <= 0:
            raise ValueError("LarguraDenteCostela deve ser maior que zero.")
        if p["rib_tooth_depth"] < 0 or p["rib_slot_clearance"] < 0:
            raise ValueError("Profundidade e folga dos dentes não podem ser negativas.")
        if p["slot_corner_relief"] == "Osso de cão integrado":
            if p["slot_tool_diameter"] <= 0:
                raise ValueError("DiametroFresaRasgos deve ser maior que zero.")
            if p["dogbone_extra_clearance"] < 0:
                raise ValueError("FolgaExtraOssoDeCao não pode ser negativa.")
    if costela_parafuso_enabled(p):
        if p["rib_hole_diameter"] <= 0 or p["rib_hole_count"] < 1:
            raise ValueError("Configuração de furos das costelas inválida.")

    if p.get("t_rib_toco_clearance", 0.0) < 0:
        raise ValueError("FolgaCostelaToco não pode ser negativa.")

    if p.get("tooth_holes_frame") or p.get("tooth_holes_leg") or p.get("tooth_holes_cap") or p.get("tooth_holes_rib"):
        if p["tooth_hole_diameter"] <= 0:
            raise ValueError("DiametroFuroDente deve ser maior que zero.")
        if p["tooth_hole_count"] < 1:
            raise ValueError("QuantidadeFurosPorDente deve ser pelo menos 1.")
        if p["tooth_hole_edge"] < 0:
            raise ValueError("RecuoFuroDente não pode ser negativo.")


# =============================================================================
# Seleção e extração das linhas
# =============================================================================

def is_sketch(obj):
    return getattr(obj, "TypeId", "") == "Sketcher::SketchObject"


def has_usable_shape(obj):
    try:
        return hasattr(obj, "Shape") and len(obj.Shape.Edges) > 0
    except Exception:
        return False


def _expand_source_object(obj, result, visited):
    """Expande grupos/pastas e recolhe sketches/linhas utilizáveis recursivamente."""
    if obj is None:
        return
    try:
        if "GeradorEstruturaEsqueleto" in getattr(obj, "PropertiesList", []):
            return
    except Exception:
        pass
    key = getattr(obj, "Name", None) or id(obj)
    if key in visited:
        return
    visited.add(key)

    if is_sketch(obj) or has_usable_shape(obj):
        if obj not in result:
            result.append(obj)
        return

    children = list(getattr(obj, "Group", []) or [])
    for child in children:
        _expand_source_object(child, result, visited)


def _expand_source_list(objects):
    result = []
    visited = set()
    for obj in objects:
        _expand_source_object(obj, result, visited)
    return result


def _sibling_sources(objects):
    """
    Inclui automaticamente sketches irmãos dentro do mesmo App::Part/Group.
    Isso permite selecionar apenas o grupo ou um dos sketches do esqueleto.
    """
    expanded = _expand_source_list(objects)
    parents = []
    for obj in list(expanded):
        for parent in list(getattr(obj, "InList", []) or []):
            if hasattr(parent, "Group") and parent not in parents:
                parents.append(parent)
    if parents:
        expanded = _expand_source_list(list(expanded) + parents)
    return expanded


def selected_sources():
    """
    Respeita exatamente a seleção atual.

    - Sketch selecionado: somente esse Sketch.
    - Linha/objeto selecionado: somente esse objeto.
    - Grupo/App::Part selecionado: expande somente o conteúdo do grupo.

    Isso impede que uma travessa simples puxe automaticamente outros Sketches
    do documento e transforme a leitura em uma rede enorme.
    """
    if Gui is None:
        return []

    try:
        selection = list(Gui.Selection.getSelection())
    except Exception:
        selection = []

    if not selection:
        return []

    expanded = _expand_source_list(selection)
    App.Console.PrintMessage(
        "V4.27R: {} objeto(s) selecionado(s); {} origem(ns) processada(s).\n"
        .format(len(selection), len(expanded))
    )
    return expanded


def resolve_sources(params):
    selected = selected_sources()
    if selected:
        params.ObjetosOrigem = selected
        sketches = [obj for obj in selected if is_sketch(obj)]
        if sketches:
            params.SketchOrigem = sketches[0]
        App.Console.PrintMessage(
            "V4.27: {} origem(ns) da seleção estrita.\n".format(len(selected))
        )
        return selected

    linked_raw = list(getattr(params, "ObjetosOrigem", []) or [])
    linked = _expand_source_list(linked_raw)
    if linked:
        params.ObjetosOrigem = linked
        App.Console.PrintMessage(
            "V4.27: {} origem(ns) dos links salvos.\n".format(len(linked))
        )
        return linked

    legacy = getattr(params, "SketchOrigem", None)
    if legacy is not None:
        expanded = _expand_source_list([legacy])
        if expanded:
            params.ObjetosOrigem = expanded
            return expanded

    raise ValueError(
        "Selecione diretamente um Sketch/objeto ou selecione o Grupo que deseja processar."
    )


def straight_edge_endpoints(edge):
    vertices = list(edge.Vertexes)
    if len(vertices) < 2:
        raise ValueError("Foi encontrada uma aresta sem dois vértices.")

    p0 = App.Vector(vertices[0].Point)
    p1 = App.Vector(vertices[-1].Point)
    chord = vector_distance(p0, p1)

    if chord <= TOL:
        raise ValueError("Foi encontrada uma linha de comprimento nulo.")

    # Para uma linha reta, o comprimento da aresta coincide com a corda.
    if abs(float(edge.Length) - chord) > max(1e-4, chord * 1e-6):
        raise ValueError(
            "Há uma aresta curva. Esta revisão aceita somente segmentos retos."
        )

    return p0, p1


def extract_from_sketch(sketch):
    edges = []
    for index, geometry in enumerate(sketch.Geometry):
        try:
            if sketch.getConstruction(index):
                continue
        except Exception:
            pass

        if not hasattr(geometry, "StartPoint") or not hasattr(geometry, "EndPoint"):
            raise ValueError(
                "O Sketch contém arco, círculo ou spline. Use somente linhas retas."
            )

        p0 = sketch.Placement.multVec(
            App.Vector(geometry.StartPoint.x, geometry.StartPoint.y, 0.0)
        )
        p1 = sketch.Placement.multVec(
            App.Vector(geometry.EndPoint.x, geometry.EndPoint.y, 0.0)
        )
        p0 = App.Vector(p0)
        p1 = App.Vector(p1)
        if vector_distance(p0, p1) <= TOL:
            App.Console.PrintWarning(
                "Linha nula ignorada em {} / geometria {}.\n".format(
                    getattr(sketch, "Label", sketch.Name), index
                )
            )
            continue
        edges.append({
            "p0": p0,
            "p1": p1,
            "source": sketch,
        })
    return edges


def extract_from_shape(obj):
    edges = []
    for edge in obj.Shape.Edges:
        p0, p1 = straight_edge_endpoints(edge)
        edges.append({
            "p0": p0,
            "p1": p1,
            "source": obj,
        })
    return edges


def quantized_point(point, scale=1e5):
    return (
        int(round(point.x * scale)),
        int(round(point.y * scale)),
        int(round(point.z * scale)),
    )


def edge_key(edge):
    a = quantized_point(edge["p0"])
    b = quantized_point(edge["p1"])
    return tuple(sorted((a, b)))


def deduplicate_edges(edges):
    result = []
    seen = set()

    for edge in edges:
        if vector_distance(edge["p0"], edge["p1"]) <= TOL:
            continue
        a = quantized_point(edge["p0"])
        b = quantized_point(edge["p1"])
        key = tuple(sorted((a, b)))
        if key in seen:
            continue
        seen.add(key)
        result.append(edge)

    if not result:
        raise ValueError("Nenhuma linha reta foi encontrada nas origens.")

    return result


def extract_all_edges(sources):
    edges = []
    for obj in sources:
        if is_sketch(obj):
            edges.extend(extract_from_sketch(obj))
        elif has_usable_shape(obj):
            edges.extend(extract_from_shape(obj))

    return deduplicate_edges(edges)


# =============================================================================
# Grafo 3D do esqueleto
# =============================================================================

def cluster_node(nodes, point):
    for index, existing in enumerate(nodes):
        if vector_distance(existing, point) <= PLANAR_TOL:
            return index
    nodes.append(App.Vector(point))
    return len(nodes) - 1


def build_graph(edges):
    nodes = []
    graph_edges = []

    for edge_index, edge in enumerate(edges):
        n0 = cluster_node(nodes, edge["p0"])
        n1 = cluster_node(nodes, edge["p1"])
        if n0 == n1:
            raise ValueError("Há uma linha degenerada no esqueleto.")
        graph_edges.append({
            "index": edge_index,
            "n0": n0,
            "n1": n1,
            "p0": App.Vector(edge["p0"]),
            "p1": App.Vector(edge["p1"]),
            "source": edge["source"],
        })

    adjacency = {index: [] for index in range(len(nodes))}
    for graph_index, edge in enumerate(graph_edges):
        adjacency[edge["n0"]].append(graph_index)
        adjacency[edge["n1"]].append(graph_index)

    return nodes, graph_edges, adjacency


def edge_other_node(edge, node_index):
    if edge["n0"] == node_index:
        return edge["n1"]
    if edge["n1"] == node_index:
        return edge["n0"]
    raise ValueError("Aresta não pertence ao nó informado.")


def find_two_core(graph_edges, adjacency):
    """Remove folhas iterativamente. O restante contém os ciclos."""
    active = set(range(len(graph_edges)))
    degree = {
        node: len(edge_ids)
        for node, edge_ids in adjacency.items()
    }
    queue = [node for node, value in degree.items() if value < 2]
    removed_nodes = set()

    while queue:
        node = queue.pop()
        if node in removed_nodes:
            continue
        removed_nodes.add(node)

        for edge_id in adjacency[node]:
            if edge_id not in active:
                continue
            active.remove(edge_id)
            edge = graph_edges[edge_id]
            other = edge_other_node(edge, node)
            degree[other] -= 1
            if degree[other] < 2:
                queue.append(other)

    return active


def connected_edge_components(edge_ids, graph_edges, adjacency):
    edge_ids = set(edge_ids)
    components = []

    while edge_ids:
        first = next(iter(edge_ids))
        stack = [first]
        component = set()

        while stack:
            edge_id = stack.pop()
            if edge_id in component:
                continue
            component.add(edge_id)
            edge_ids.discard(edge_id)

            edge = graph_edges[edge_id]
            for node in (edge["n0"], edge["n1"]):
                for neighbor in adjacency[node]:
                    if neighbor in edge_ids and neighbor not in component:
                        stack.append(neighbor)

        components.append(component)

    return components


def order_cycle(edge_ids, nodes, graph_edges, adjacency):
    edge_ids = set(edge_ids)
    if len(edge_ids) < 3:
        raise ValueError("O ciclo planar precisa ter pelo menos três lados.")

    cycle_nodes = set()
    for edge_id in edge_ids:
        edge = graph_edges[edge_id]
        cycle_nodes.add(edge["n0"])
        cycle_nodes.add(edge["n1"])

    for node in cycle_nodes:
        count = sum(1 for edge_id in adjacency[node] if edge_id in edge_ids)
        if count != 2:
            raise ValueError(
                "O núcleo cíclico não forma um único contorno simples."
            )

    start = next(iter(cycle_nodes))
    current = start
    previous_edge = None
    ordered_nodes = [start]
    ordered_edges = []
    used = set()

    while True:
        candidates = [
            edge_id for edge_id in adjacency[current]
            if edge_id in edge_ids and edge_id != previous_edge
        ]
        if not candidates:
            raise ValueError("Não foi possível percorrer o ciclo.")

        edge_id = candidates[0]
        if edge_id in used:
            break

        used.add(edge_id)
        ordered_edges.append(edge_id)

        edge = graph_edges[edge_id]
        next_node = edge_other_node(edge, current)
        previous_edge = edge_id
        current = next_node

        if current == start:
            break

        ordered_nodes.append(current)

        if len(ordered_nodes) > len(cycle_nodes) + 1:
            raise ValueError("Falha ao ordenar o ciclo.")

    if used != edge_ids or current != start:
        raise ValueError("O ciclo não é fechado ou possui ramificações internas.")

    return [App.Vector(nodes[index]) for index in ordered_nodes], ordered_edges


# =============================================================================
# Plano, projeção e contorno externo
# =============================================================================

def first_valid_normal(vertices):
    origin = vertices[0]
    for i in range(1, len(vertices) - 1):
        a = vertices[i].sub(origin)
        for j in range(i + 1, len(vertices)):
            b = vertices[j].sub(origin)
            cross = a.cross(b)
            if cross.Length > TOL:
                return vector_unit(cross)
    raise ValueError("Os pontos do contorno são colineares.")


def point_on_loop_index(point, loop_vertices):
    for index, vertex in enumerate(loop_vertices):
        if vector_distance(point, vertex) <= PLANAR_TOL:
            return index
    return None


def choose_plane_normal(
    raw_normal,
    loop_vertices,
    remaining_edges,
    direction_mode,
):
    normal = App.Vector(raw_normal)

    if direction_mode == "Oposta à normal":
        return normal.multiply(-1.0)

    if direction_mode == "Normal do contorno":
        return normal

    # Automática: procura linhas ligadas aos vértices e quase perpendiculares
    # ao plano. O quadro é extrudado na direção dessas linhas.
    direction_sum = App.Vector(0.0, 0.0, 0.0)

    for edge in remaining_edges:
        index0 = point_on_loop_index(edge["p0"], loop_vertices)
        index1 = point_on_loop_index(edge["p1"], loop_vertices)

        if index0 is not None and index1 is None:
            vector = edge["p1"].sub(edge["p0"])
        elif index1 is not None and index0 is None:
            vector = edge["p0"].sub(edge["p1"])
        else:
            continue

        if vector.Length <= TOL:
            continue
        unit = vector_unit(vector)
        if abs(unit.dot(normal)) >= 0.95:
            direction_sum = direction_sum.add(unit)

    if direction_sum.Length > TOL and direction_sum.dot(normal) < 0:
        normal = normal.multiply(-1.0)

    return normal


def plane_basis(vertices, remaining_edges, direction_mode):
    raw_normal = first_valid_normal(vertices)

    # Verifica coplanaridade em relação à normal geométrica inicial.
    origin = vertices[0]
    for point in vertices:
        distance = abs(point.sub(origin).dot(raw_normal))
        if distance > PLANAR_TOL:
            raise ValueError(
                "O contorno detectado não é planar. "
                "Use Rede 3D por eixos ou corrija os pontos."
            )

    normal = choose_plane_normal(
        raw_normal,
        vertices,
        remaining_edges,
        direction_mode,
    )

    axis_u = vector_unit(vertices[1].sub(vertices[0]))
    axis_v = vector_unit(normal.cross(axis_u))

    def project(point):
        delta = point.sub(origin)
        return (
            delta.dot(axis_u),
            delta.dot(axis_v),
        )

    projected = [project(point) for point in vertices]
    if signed_area(projected) < 0:
        vertices = list(reversed(vertices))
        origin = vertices[0]
        axis_u = vector_unit(vertices[1].sub(vertices[0]))
        axis_v = vector_unit(normal.cross(axis_u))

        def project(point):
            delta = point.sub(origin)
            return (
                delta.dot(axis_u),
                delta.dot(axis_v),
            )

        projected = [project(point) for point in vertices]

    return {
        "origin": origin,
        "normal": normal,
        "axis_u": axis_u,
        "axis_v": axis_v,
        "vertices": vertices,
        "projected": projected,
    }


def signed_area(vertices_2d):
    area = 0.0
    for index, point in enumerate(vertices_2d):
        other = vertices_2d[(index + 1) % len(vertices_2d)]
        area += point[0] * other[1] - other[0] * point[1]
    return area / 2.0


def ensure_convex(vertices_2d):
    signs = []
    count = len(vertices_2d)

    for index in range(count):
        a = vertices_2d[index - 1]
        b = vertices_2d[index]
        c = vertices_2d[(index + 1) % count]

        ab = (b[0] - a[0], b[1] - a[1])
        bc = (c[0] - b[0], c[1] - b[1])
        cross = ab[0] * bc[1] - ab[1] * bc[0]

        if abs(cross) <= TOL:
            raise ValueError(
                "Há lados consecutivos colineares no contorno."
            )
        signs.append(cross)

    if any(value < -TOL for value in signs):
        raise ValueError(
            "Nesta revisão, o limite externo deve ser convexo."
        )


def add2d(a, b):
    return (a[0] + b[0], a[1] + b[1])


def sub2d(a, b):
    return (a[0] - b[0], a[1] - b[1])


def mul2d(a, scalar):
    return (a[0] * scalar, a[1] * scalar)


def dot2d(a, b):
    return a[0] * b[0] + a[1] * b[1]


def cross2d(a, b):
    return a[0] * b[1] - a[1] * b[0]


def normalize2d(vector):
    length = math.hypot(vector[0], vector[1])
    if length <= TOL:
        raise ValueError("Segmento de comprimento nulo.")
    return (vector[0] / length, vector[1] / length), length


def line_intersection(point_a, direction_a, point_b, direction_b):
    denominator = cross2d(direction_a, direction_b)
    if abs(denominator) <= TOL:
        raise ValueError(
            "Não foi possível calcular a meia-esquadria entre lados paralelos."
        )
    delta = sub2d(point_b, point_a)
    parameter = cross2d(delta, direction_b) / denominator
    return add2d(point_a, mul2d(direction_a, parameter))


def calculate_planar_segments(plane, profile_width, connection):
    vertices_2d = plane["projected"]
    vertices_3d = plane["vertices"]
    normal = plane["normal"]
    count = len(vertices_2d)

    ensure_convex(vertices_2d)

    directions_2d = []
    lengths = []
    offset_points = []

    for index in range(count):
        start = vertices_2d[index]
        end = vertices_2d[(index + 1) % count]
        direction, length = normalize2d(sub2d(end, start))
        inward = (-direction[1], direction[0])
        directions_2d.append(direction)
        lengths.append(length)
        offset_points.append(add2d(start, mul2d(inward, profile_width)))

    segments = []

    for index in range(count):
        start_2d = vertices_2d[index]
        direction_2d = directions_2d[index]
        length = lengths[index]

        if connection == "Meia-esquadria automática":
            previous = (index - 1) % count
            following = (index + 1) % count

            inner_start = line_intersection(
                offset_points[previous],
                directions_2d[previous],
                offset_points[index],
                directions_2d[index],
            )
            inner_end = line_intersection(
                offset_points[index],
                directions_2d[index],
                offset_points[following],
                directions_2d[following],
            )

            start_u = dot2d(sub2d(inner_start, start_2d), direction_2d)
            end_u = dot2d(sub2d(inner_end, start_2d), direction_2d)

            if end_u - start_u <= max(TOL, profile_width * 0.02):
                raise ValueError(
                    "LarguraPerfil é grande demais para um dos lados."
                )
        else:
            start_u = 0.0
            end_u = length

        start_3d = vertices_3d[index]
        end_3d = vertices_3d[(index + 1) % count]
        axis_x = vector_unit(end_3d.sub(start_3d))
        axis_y = vector_unit(normal.cross(axis_x))
        axis_z = App.Vector(normal)

        footprint = [
            (0.0, 0.0),
            (length, 0.0),
            (end_u, profile_width),
            (start_u, profile_width),
        ]

        segments.append({
            "kind": "planar",
            "index": index + 1,
            "start": start_3d,
            "end": end_3d,
            "length": length,
            "axis_x": axis_x,
            "axis_y": axis_y,
            "axis_z": axis_z,
            "footprint": footprint,
        })

    return segments


# =============================================================================
# Identificação de pernas e bases de rede 3D
# =============================================================================

def stable_axis_basis(line_direction):
    """
    Para rede 3D:
      local Z = direção da linha;
      local Y tenta permanecer vertical no mundo;
      local X completa a base ortogonal.
    """
    axis_z = vector_unit(line_direction)
    global_up = App.Vector(0.0, 0.0, 1.0)

    projection = global_up.sub(
        App.Vector(axis_z).multiply(global_up.dot(axis_z))
    )

    if projection.Length > 1e-5:
        axis_y = vector_unit(projection)
        axis_x = vector_unit(axis_y.cross(axis_z))
    else:
        axis_x = App.Vector(1.0, 0.0, 0.0)
        if abs(axis_x.dot(axis_z)) > 0.95:
            axis_x = App.Vector(0.0, 1.0, 0.0)
        axis_x = vector_unit(
            axis_x.sub(vector_scaled(axis_z, axis_x.dot(axis_z)))
        )
        axis_y = vector_unit(axis_z.cross(axis_x))

    return axis_x, axis_y, axis_z


def loop_corner_axes(loop_vertices, vertex_index):
    count = len(loop_vertices)
    vertex = loop_vertices[vertex_index]
    next_vertex = loop_vertices[(vertex_index + 1) % count]
    previous_vertex = loop_vertices[(vertex_index - 1) % count]

    to_next = vector_unit(next_vertex.sub(vertex))
    to_previous = vector_unit(previous_vertex.sub(vertex))

    return to_next, to_previous


def find_attached_loop_vertex(edge, loop_vertices, tolerance=PLANAR_TOL):
    def close_index(point):
        for index, vertex in enumerate(loop_vertices):
            if vector_distance(point, vertex) <= tolerance:
                return index
        return None

    index0 = close_index(edge["p0"])
    index1 = close_index(edge["p1"])

    if index0 is not None and index1 is None:
        return index0, edge["p0"], edge["p1"]
    if index1 is not None and index0 is None:
        return index1, edge["p1"], edge["p0"]
    return None


def project_point_to_segment(point, start, end):
    vector = end.sub(start)
    length2 = vector.dot(vector)
    if length2 <= TOL:
        return 0.0, App.Vector(start), vector_distance(point, start)
    t = clamp(point.sub(start).dot(vector) / length2, 0.0, 1.0)
    projected = start.add(vector.multiply(t))
    return t, projected, vector_distance(point, projected)


def find_attached_loop_edge(edge, loop_vertices, tolerance):
    candidates = []
    for endpoint_name, attached_point, other_point in (
        ("p0", edge["p0"], edge["p1"]),
        ("p1", edge["p1"], edge["p0"]),
    ):
        for index in range(len(loop_vertices)):
            start = loop_vertices[index]
            end = loop_vertices[(index + 1) % len(loop_vertices)]
            t, projected, distance = project_point_to_segment(attached_point, start, end)
            if distance <= tolerance and t > 1e-5 and t < 1.0 - 1e-5:
                candidates.append((distance, index, t, projected, attached_point, other_point))
    if not candidates:
        return None
    candidates.sort(key=lambda item: item[0])
    distance, index, t, projected, attached_point, other_point = candidates[0]
    segment_length = vector_distance(loop_vertices[index], loop_vertices[(index + 1) % len(loop_vertices)])
    return {
        "segment_index": index,
        "segment_t": t,
        "segment_u": t * segment_length,
        "attached_point": App.Vector(projected),
        "other_point": App.Vector(other_point),
        "distance": distance,
    }


def create_network_descriptors(remaining_edges, plane, p):
    descriptors = []
    anchored_count = 0
    corner_count = 0
    edge_count = 0
    leg_w, leg_d = leg_dimensions(p)

    for index, edge in enumerate(remaining_edges, start=1):
        line = edge["p1"].sub(edge["p0"])
        length = line.Length
        if length <= TOL:
            App.Console.PrintWarning(
                "Elemento nulo ignorado na rede secundária: {}.\n".format(index)
            )
            continue

        created = False
        corner_attachment = None
        edge_attachment = None

        if plane is not None:
            try:
                corner_attachment = find_attached_loop_vertex(
                    edge, plane["vertices"], p["attach_tolerance"]
                )
                if corner_attachment is None:
                    edge_attachment = find_attached_loop_edge(
                        edge, plane["vertices"], p["attach_tolerance"]
                    )
            except Exception:
                corner_attachment = None
                edge_attachment = None

        if corner_attachment is not None:
            try:
                vertex_index, attached_point, other_point = corner_attachment
                delta_dir = other_point.sub(attached_point)
                if delta_dir.Length > TOL:
                    direction = vector_unit(delta_dir)
                    perpendicularity = abs(direction.dot(plane["normal"]))
                    axis_x, axis_y = loop_corner_axes(
                        plane["vertices"], vertex_index
                    )
                    orthogonality = abs(axis_x.dot(axis_y))

                    if perpendicularity >= 0.95 and orthogonality <= 0.05:
                        if axis_x.cross(axis_y).dot(direction) < 0:
                            axis_x, axis_y = axis_y, axis_x
                        if p["corner_legs"] == "Linha no centro do perfil":
                            origin = (
                                App.Vector(attached_point)
                                .sub(vector_scaled(axis_x, leg_w / 2.0))
                                .sub(vector_scaled(axis_y, leg_d / 2.0))
                            )
                        else:
                            origin = App.Vector(attached_point)
                        descriptors.append({
                            "kind": "axis_corner",
                            "index": index,
                            "corner_index": vertex_index,
                            "start": App.Vector(edge["p0"]),
                            "end": App.Vector(edge["p1"]),
                            "origin": origin,
                            "length": length,
                            "axis_x": axis_x,
                            "axis_y": axis_y,
                            "axis_z": direction,
                            "source": edge["source"],
                        })
                        anchored_count += 1
                        corner_count += 1
                        created = True
            except Exception as exc:
                App.Console.PrintWarning(
                    "Conexão de canto {} reinterpretada como barra: {}.\n".format(
                        index, exc
                    )
                )

        if not created and edge_attachment is not None:
            try:
                attached_point = edge_attachment["attached_point"]
                other_point = edge_attachment["other_point"]
                delta_dir = other_point.sub(attached_point)
                if delta_dir.Length > TOL:
                    direction = vector_unit(delta_dir)
                    perpendicularity = abs(direction.dot(plane["normal"]))
                    if perpendicularity >= 0.95:
                        segment_index = edge_attachment["segment_index"]
                        start_point = plane["vertices"][segment_index]
                        end_point = plane["vertices"][
                            (segment_index + 1) % len(plane["vertices"])
                        ]
                        segment_vector = end_point.sub(start_point)
                        if segment_vector.Length > TOL:
                            original_x = vector_unit(segment_vector)
                            inward_vector = plane["normal"].cross(original_x)
                            if inward_vector.Length > TOL:
                                inward = vector_unit(inward_vector)
                                axis_x = App.Vector(original_x)
                                if axis_x.cross(inward).dot(direction) < 0:
                                    axis_x = axis_x.multiply(-1.0)
                                origin = attached_point.sub(
                                    vector_scaled(axis_x, leg_w / 2.0)
                                )
                                descriptors.append({
                                    "kind": "axis_edge",
                                    "index": index,
                                    "edge_segment_index": segment_index,
                                    "edge_u": edge_attachment["segment_u"],
                                    "start": App.Vector(edge["p0"]),
                                    "end": App.Vector(edge["p1"]),
                                    "origin": origin,
                                    "length": length,
                                    "axis_x": axis_x,
                                    "axis_y": inward,
                                    "axis_z": direction,
                                    "source": edge["source"],
                                })
                                anchored_count += 1
                                edge_count += 1
                                created = True
            except Exception as exc:
                App.Console.PrintWarning(
                    "Conexão intermediária {} reinterpretada como barra: {}.\n".format(
                        index, exc
                    )
                )

        if created:
            continue

        try:
            axis_x, axis_y, axis_z = stable_axis_basis(line)
        except Exception as exc:
            App.Console.PrintWarning(
                "Elemento secundário {} ignorado: {}.\n".format(index, exc)
            )
            continue

        descriptors.append({
            "kind": "axis_center",
            "index": index,
            "start": App.Vector(edge["p0"]),
            "end": App.Vector(edge["p1"]),
            "origin": App.Vector(edge["p0"]),
            "length": length,
            "axis_x": axis_x,
            "axis_y": axis_y,
            "axis_z": axis_z,
            "source": edge["source"],
        })

    return descriptors, anchored_count, corner_count, edge_count


# =============================================================================
# Criação de Sketches, Pads e vazamentos
# =============================================================================

def clear_generated(doc):
    """Remove apenas objetos da versão segura. Não toca nas versões antigas."""
    targets = []
    for obj in list(doc.Objects):
        try:
            if "GeradorEstruturaEsqueleto" in obj.PropertiesList:
                tag = str(obj.GeradorEstruturaEsqueleto)
                if tag in (
                    GENERATOR_TAG,
                    "Gerador_Estrutura_Esqueleto_v4_26",
                    "Gerador_Estrutura_Esqueleto_v4_25",
                    "Gerador_Estrutura_Esqueleto_v4_24",
                    "Gerador_Estrutura_Esqueleto_v4_23",
                    "Gerador_Estrutura_Esqueleto_v4_22",
                    "Gerador_Estrutura_Esqueleto_v4_21",
                    "Gerador_Estrutura_Esqueleto_v4_20",
                    "Gerador_Estrutura_Esqueleto_v4_19",
                    "Gerador_Estrutura_Esqueleto_v4_18",
                    "Gerador_Estrutura_Esqueleto_v4_17",
                    "Gerador_Estrutura_Esqueleto_v4_16",
                    "Gerador_Estrutura_Esqueleto_v4_15",
                    "Gerador_Estrutura_Esqueleto_v4_14",
                    "Gerador_Estrutura_Esqueleto_v4_13",
                    "Gerador_Estrutura_Esqueleto_v4_12",
                    "Gerador_Estrutura_Esqueleto_v4_11",
                    "Gerador_Estrutura_Esqueleto_v4_10",
                    "Gerador_Estrutura_Esqueleto_v4_7",
                    "Gerador_Estrutura_Esqueleto_v4_6",
                    "Gerador_Estrutura_Esqueleto_v4_5",
                    "Gerador_Estrutura_Esqueleto_v4_4",
                    "Gerador_Estrutura_Esqueleto_v4_3",
                    "Gerador_Estrutura_Esqueleto_v4_2",
                    "Gerador_Estrutura_Esqueleto_v4_1",
                    "Gerador_Estrutura_Esqueleto_v4",
                    "Gerador_Estrutura_Esqueleto_v3_SAFE_TOCO",
                    "Gerador_Estrutura_Esqueleto_v2_SAFE",
                ):
                    targets.append(obj)
        except Exception:
            pass

    # Filhos primeiro. Objetos sem filhos costumam aparecer depois dos grupos,
    # mas a ordenação por profundidade do InList torna a remoção mais segura.
    def depth(obj):
        visited = set()
        stack = list(getattr(obj, "InList", []) or [])
        count = 0
        while stack and count < 100:
            parent = stack.pop()
            if parent.Name in visited:
                continue
            visited.add(parent.Name)
            count += 1
            stack.extend(list(getattr(parent, "InList", []) or []))
        return count

    for obj in sorted(targets, key=depth, reverse=True):
        try:
            if doc.getObject(obj.Name) is not None:
                doc.removeObject(obj.Name)
        except Exception:
            pass
    doc.recompute()


def add_polygon_to_sketch(sketch, polygon):
    """Mantido por compatibilidade; a versão segura não cria Pads."""
    geometry = []
    for index, point in enumerate(polygon):
        other = polygon[(index + 1) % len(polygon)]
        distance = math.hypot(point[0] - other[0], point[1] - other[1])
        if distance <= TOL:
            continue
        geometry.append(
            Part.LineSegment(
                App.Vector(point[0], point[1], 0.0),
                App.Vector(other[0], other[1], 0.0),
            )
        )
    if len(geometry) < 3:
        raise ValueError("Polígono inválido.")
    sketch.addGeometry(geometry, False)


def merge_intervals(intervals, lower=0.0, upper=None):
    cleaned = []
    for a, b in intervals:
        if upper is not None:
            a = clamp(a, lower, upper)
            b = clamp(b, lower, upper)
        if b < a:
            a, b = b, a
        if b - a > TOL:
            cleaned.append((a, b))
    cleaned.sort()
    merged = []
    for a, b in cleaned:
        if not merged or a > merged[-1][1] + TOL:
            merged.append([a, b])
        else:
            merged[-1][1] = max(merged[-1][1], b)
    return [(a, b) for a, b in merged]


def free_intervals(length, blocked):
    blocked = merge_intervals(blocked, 0.0, length)
    free = []
    cursor = 0.0
    for a, b in blocked:
        if a - cursor > TOL:
            free.append((cursor, a))
        cursor = max(cursor, b)
    if length - cursor > TOL:
        free.append((cursor, length))
    return free


def calculate_rib_centers(length, p, blocked_intervals=None):
    if not p["create_ribs"]:
        return []
    blocked_intervals = blocked_intervals or []
    free = free_intervals(length, blocked_intervals)
    if not free:
        return []

    centers = []
    if p["rib_count_manual"] > 0:
        total_free = sum(b - a for a, b in free)
        if total_free <= TOL:
            return []
        spacing = total_free / float(p["rib_count_manual"] + 1)
        targets = [spacing * i for i in range(1, p["rib_count_manual"] + 1)]
        cumulative = 0.0
        for target in targets:
            for a, b in free:
                span = b - a
                if target <= cumulative + span + TOL:
                    centers.append(a + (target - cumulative))
                    break
                cumulative += span
            cumulative = 0.0
    else:
        for a, b in free:
            span = b - a
            count = int(math.floor(span / p["rib_max_span"] + 1e-9))
            if count <= 0:
                continue
            spacing = span / float(count + 1)
            centers.extend(a + spacing * i for i in range(1, count + 1))

    return [c for c in centers if c > TOL and c < length - TOL]


def rib_dimensions(p):
    available_width = p["profile_width"] - 2.0 * p["wall"] - 2.0 * p["rib_clearance"]
    available_height = p["profile_height"] - 2.0 * p["wall"] - 2.0 * p["rib_clearance"]
    width = p["rib_width_manual"] if p["rib_width_manual"] > TOL else available_width
    height = p["rib_height_manual"] if p["rib_height_manual"] > TOL else available_height
    if width <= 0 or height <= 0:
        raise ValueError("A folga deixa a costela com dimensão inválida.")
    if width > available_width + TOL or height > available_height + TOL:
        raise ValueError("A dimensão manual da costela ultrapassa a cavidade.")
    return width, height


def distributed_ranges(start, length, count, item_width):
    if count < 1:
        return []
    item_width = min(item_width, length / max(1.0, count * 1.5))
    spacing = length / float(count + 1)
    result = []
    for i in range(1, count + 1):
        center = start + spacing * i
        result.append((center - item_width / 2.0, center + item_width / 2.0))
    return result


def selected_rib_sides(p):
    mode = p["rib_tab_sides"]
    if mode == "2 lados opostos":
        return ("outer", "inner")
    if mode == "3 lados":
        return ("outer", "inner", "lower")
    return ("outer", "inner", "lower", "upper")


def _cut_planar_rib_tab_holes(tab, p, x0, centers_yz, context):
    """Fura um dente de costela planar no eixo local X."""
    if not p.get("tooth_holes_rib", False):
        return tab
    radius = p["tooth_hole_diameter"] / 2.0
    over = max(2.0, radius * 0.75)
    cutters = [
        Part.makeCylinder(
            radius,
            p["rib_thickness"] + 2.0 * over,
            App.Vector(x0 - over, y, z),
            App.Vector(1, 0, 0),
        )
        for y, z in centers_yz
    ]
    return safe_cut_shape(tab, cutters, context)


def _cut_axis_rib_tab_holes(tab, p, z0, centers_xy, context):
    """Fura um dente de costela 3D no eixo local Z."""
    if not p.get("tooth_holes_rib", False):
        return tab
    radius = p["tooth_hole_diameter"] / 2.0
    over = max(2.0, radius * 0.75)
    cutters = [
        Part.makeCylinder(
            radius,
            p["rib_thickness"] + 2.0 * over,
            App.Vector(x, y, z0 - over),
            App.Vector(0, 0, 1),
        )
        for x, y in centers_xy
    ]
    return safe_cut_shape(tab, cutters, context)


def planar_rib_shape(center, p, deep_down=False, bottom_limit_z=None):
    rib_width, rib_height = rib_dimensions(p)
    x0 = center - p["rib_thickness"] / 2.0
    y0 = p["wall"] + p["rib_clearance"]
    z0 = p["wall"] + p["rib_clearance"]
    if bottom_limit_z is not None:
        rib_height = min(rib_height, max(TOL, bottom_limit_z - z0))
    solids = [
        Part.makeBox(
            p["rib_thickness"], rib_width, rib_height,
            App.Vector(x0, y0, z0)
        )
    ]

    if costela_encaixe_enabled(p):
        depth = tooth_depth(p)
        count = p["rib_tab_count"]
        width = p["rib_tab_width"]
        for side in selected_rib_sides(p):
            if side in ("outer", "inner"):
                ranges = distributed_ranges(z0, rib_height, count, width)
                for a, b in ranges:
                    y = y0 - depth if side == "outer" else y0 + rib_width
                    tab = Part.makeBox(
                        p["rib_thickness"], depth, b - a,
                        App.Vector(x0, y, a)
                    )
                    centers = [
                        (y + depth / 2.0, zc)
                        for zc in tooth_hole_centers(a, b, p)
                    ]
                    tab = _cut_planar_rib_tab_holes(
                        tab, p, x0, centers,
                        "furos nos dentes {} da costela planar".format(side)
                    )
                    solids.append(tab)
            else:
                # A conexão T usa o dente profundo separadamente.
                if deep_down and side == "upper":
                    continue
                ranges = distributed_ranges(y0, rib_width, count, width)
                for a, b in ranges:
                    z = z0 - depth if side == "lower" else z0 + rib_height
                    tab = Part.makeBox(
                        p["rib_thickness"], b - a, depth,
                        App.Vector(x0, a, z)
                    )
                    centers = [
                        (yc, z + depth / 2.0)
                        for yc in tooth_hole_centers(a, b, p)
                    ]
                    tab = _cut_planar_rib_tab_holes(
                        tab, p, x0, centers,
                        "furos nos dentes {} da costela planar".format(side)
                    )
                    solids.append(tab)
        if deep_down:
            tooth_w = min(
                max(width, p["rib_thickness"] * 2.0),
                rib_width * 0.70,
            )
            a = y0 + (rib_width - tooth_w) / 2.0
            deep_depth = deep_lower_tooth_depth(p)
            tab = Part.makeBox(
                p["rib_thickness"], tooth_w, deep_depth,
                App.Vector(x0, a, z0 + rib_height)
            )
            centers = [
                (yc, z0 + rib_height + deep_depth / 2.0)
                for yc in tooth_hole_centers(a, a + tooth_w, p)
            ]
            tab = _cut_planar_rib_tab_holes(
                tab, p, x0, centers,
                "furos no dente profundo da costela T"
            )
            solids.append(tab)
    shape = safe_fuse_shapes(solids, "costela planar dentada")
    return safe_cut_shape(
        shape,
        male_tab_root_reliefs_rib_planar(center, p, deep_down, rib_height),
        "dogbone nas raízes da costela planar",
    )


def axis_rib_shape(center, p, centered, width=None, height=None):
    if width is None or height is None:
        width, height = rib_dimensions(p)
    if centered:
        x0 = -width / 2.0
        y0 = -height / 2.0
    else:
        x0 = p["wall"] + p["rib_clearance"]
        y0 = p["wall"] + p["rib_clearance"]
    z0 = center - p["rib_thickness"] / 2.0
    solids = [
        Part.makeBox(
            width, height, p["rib_thickness"],
            App.Vector(x0, y0, z0)
        )
    ]

    if costela_encaixe_enabled(p):
        depth = tooth_depth(p)
        count = p["rib_tab_count"]
        tab_width = p["rib_tab_width"]
        for side in selected_rib_sides(p):
            if side in ("outer", "inner"):
                ranges = distributed_ranges(y0, height, count, tab_width)
                for a, b in ranges:
                    x = x0 - depth if side == "outer" else x0 + width
                    tab = Part.makeBox(
                        depth, b - a, p["rib_thickness"],
                        App.Vector(x, a, z0)
                    )
                    centers = [
                        (x + depth / 2.0, yc)
                        for yc in tooth_hole_centers(a, b, p)
                    ]
                    tab = _cut_axis_rib_tab_holes(
                        tab, p, z0, centers,
                        "furos nos dentes {} da costela 3D".format(side)
                    )
                    solids.append(tab)
            else:
                ranges = distributed_ranges(x0, width, count, tab_width)
                for a, b in ranges:
                    y = y0 - depth if side == "lower" else y0 + height
                    tab = Part.makeBox(
                        b - a, depth, p["rib_thickness"],
                        App.Vector(a, y, z0)
                    )
                    centers = [
                        (xc, y + depth / 2.0)
                        for xc in tooth_hole_centers(a, b, p)
                    ]
                    tab = _cut_axis_rib_tab_holes(
                        tab, p, z0, centers,
                        "furos nos dentes {} da costela 3D".format(side)
                    )
                    solids.append(tab)
    shape = safe_fuse_shapes(solids, "costela 3D dentada")
    return safe_cut_shape(
        shape,
        male_tab_root_reliefs_rib_axis(center, p, centered, width, height),
        "dogbone nas raízes da costela 3D",
    )

def face_from_polygon_2d(points, z=0.0):
    vectors = [App.Vector(x, y, z) for x, y in points]
    vectors.append(App.Vector(points[0][0], points[0][1], z))
    wire = Part.makePolygon(vectors)
    return Part.Face(wire)


def x_at_depth(outer_x, inner_x, depth, total_width):
    return outer_x + (inner_x - outer_x) * (depth / total_width)


def clip_polygon_x(points, x_min, x_max):
    def clip(points_in, keep, intersect):
        if not points_in:
            return []
        output = []
        previous = points_in[-1]
        previous_inside = keep(previous)
        for current in points_in:
            current_inside = keep(current)
            if current_inside:
                if not previous_inside:
                    output.append(intersect(previous, current))
                output.append(current)
            elif previous_inside:
                output.append(intersect(previous, current))
            previous = current
            previous_inside = current_inside
        return output

    def intersect_at_x(a, b, x):
        dx = b[0] - a[0]
        if abs(dx) <= TOL:
            return (x, a[1])
        t = (x - a[0]) / dx
        return (x, a[1] + t * (b[1] - a[1]))

    result = clip(points, lambda p: p[0] >= x_min - TOL,
                  lambda a, b: intersect_at_x(a, b, x_min))
    result = clip(result, lambda p: p[0] <= x_max + TOL,
                  lambda a, b: intersect_at_x(a, b, x_max))
    return result


def _cutters_are_disjoint(cutter_a, cutter_b, tolerance=1e-7):
    """Retorna se duas ferramentas não se tocam nem se sobrepõem.

    A decisão é feita pela caixa envolvente e é conservadora: caixas que só
    encostam continuam no caminho individual. Isso preserva a mesma geometria
    da sequência de cortes, mas permite agrupar rasgos bem separados.
    """
    box_a = cutter_a.BoundBox
    box_b = cutter_b.BoundBox
    return (
        box_a.XMax < box_b.XMin - tolerance
        or box_b.XMax < box_a.XMin - tolerance
        or box_a.YMax < box_b.YMin - tolerance
        or box_b.YMax < box_a.YMin - tolerance
        or box_a.ZMax < box_b.ZMin - tolerance
        or box_b.ZMax < box_a.ZMin - tolerance
    )


def _disjoint_cut_batches(cutters, maximum_size=8):
    """Divide ferramentas em lotes pequenos cujas caixas não se cruzam."""
    batches = []
    for cutter in cutters:
        placed = False
        for batch in batches:
            if (
                len(batch) < maximum_size
                and all(_cutters_are_disjoint(cutter, other) for other in batch)
            ):
                batch.append(cutter)
                placed = True
                break
        if not placed:
            batches.append([cutter])
    return batches


def safe_cut_shape(shape, cutters, context):
    """
    Corta cada rasgo separadamente.

    Cortar um Compound com dezenas de ferramentas sobrepostas fazia o OCC
    desistir da operação inteira e deixava o painel liso. Na V4.5, a falha
    de um rasgo não cancela os demais.
    """
    if not cutters:
        return shape

    result = shape
    failed = 0
    processed = 0
    for batch in _disjoint_cut_batches(cutters):
        # Cortes em ferramentas separadas comutam: cortar o composto é
        # geometricamente idêntico a cortá-las uma a uma.  Lotes pequenos
        # evitam o problema antigo de compostos enormes/sobrepostos no OCC.
        pending = list(batch)
        if len(batch) > 1:
            try:
                candidate = result.cut(Part.makeCompound(batch))
                if candidate.isNull() or not candidate.isValid():
                    raise ValueError("resultado de lote inválido")
                result = candidate
                processed += len(batch)
                pending = []
            except Exception:
                # O fallback abaixo mantém o comportamento robusto original.
                pending = list(batch)

        for cutter in pending:
            processed += 1
            try:
                candidate = result.cut(cutter)
                if candidate.isNull():
                    raise ValueError("resultado nulo")
                result = candidate
            except Exception as exc:
                failed += 1
                App.Console.PrintWarning(
                    "Rasgo {}/{} ignorado em {}: {}.\\n".format(
                        processed, len(cutters), context, exc
                    )
                )

    if failed:
        App.Console.PrintWarning(
            "{}: {} de {} rasgo(s) não puderam ser subtraídos; os demais foram mantidos.\\n".format(
                context, failed, len(cutters)
            )
        )
    return result


def dogbone_enabled(p):
    # O alívio é global. Para costelas, os rasgos só são chamados quando
    # GerarRasgosReais está ativo. Para os dentes do quadro, os rasgos
    # complementares fazem parte da própria união dentada.
    return p.get("slot_corner_relief") == "Osso de cão integrado"


def dogbone_radius(p):
    return p["slot_tool_diameter"] / 2.0 + p["dogbone_extra_clearance"]


def dogbone_centers(u0, u1, v0, v1, radius, p, open_side=None):
    """
    Centros do alívio no sistema 2D local do rasgo.

    open_side pode ser u_min, u_max, v_min ou v_max. Em rasgos abertos
    pela borda, somente os dois cantos internos fechados recebem alívio.

    Na orientação automática, o centro se desloca pelo eixo curto do
    rasgo. Isso mantém o alívio "deitado" em rasgos altos e "em pé" em
    rasgos largos, sempre baseado na geometria local da peça — nunca em
    X/Y/Z globais.
    """
    corners = [
        (u0, v0, -1.0, -1.0, "u_min", "v_min"),
        (u0, v1, -1.0, +1.0, "u_min", "v_max"),
        (u1, v0, +1.0, -1.0, "u_max", "v_min"),
        (u1, v1, +1.0, +1.0, "u_max", "v_max"),
    ]
    if open_side:
        corners = [item for item in corners if open_side not in (item[4], item[5])]

    overlap = max(0.20, radius * 0.22)
    offset = max(radius * 0.35, radius - overlap)
    diagonal = p.get("dogbone_orientation") == "Diagonal clássica"
    du = abs(u1 - u0)
    dv = abs(v1 - v0)
    use_u = du <= dv

    centers = []
    for u, v, su, sv, _uside, _vside in corners:
        if diagonal:
            diag = max(radius * 0.20, radius / math.sqrt(2.0) - overlap * 0.35)
            centers.append((u + su * diag, v + sv * diag))
        elif open_side in ("v_min", "v_max"):
            # Entalhe aberto em V: alívio lateral nos dois cantos fechados.
            centers.append((u + su * offset, v))
        elif open_side in ("u_min", "u_max"):
            # Entalhe aberto em U: alívio acima/abaixo nos cantos fechados.
            centers.append((u, v + sv * offset))
        elif use_u:
            centers.append((u + su * offset, v))
        else:
            centers.append((u, v + sv * offset))
    return tuple(centers)

def fuse_slot_components(base, additions, context):
    """Une os lóbulos de alívio ao rasgo e devolve uma única ferramenta contínua."""
    result = base
    try:
        for addition in additions:
            result = result.fuse(addition)
        result = result.removeSplitter()
        if result.isNull():
            raise ValueError("resultado nulo")
        return result
    except Exception as exc:
        App.Console.PrintWarning(
            "Osso de cão não pôde ser integrado em {}: {}. Mantido rasgo retangular.\\n".format(
                context, exc
            )
        )
        return base


def plain_slot_xy(x0, x1, y0, y1, z0, depth):
    return Part.makeBox(x1 - x0, y1 - y0, depth, App.Vector(x0, y0, z0))


def integrated_slot_xy(x0, x1, y0, y1, z0, depth, p, open_side=None):
    base = Part.makeBox(x1 - x0, y1 - y0, depth, App.Vector(x0, y0, z0))
    if not dogbone_enabled(p):
        return base
    radius = dogbone_radius(p)
    circles = [
        Part.makeCylinder(radius, depth, App.Vector(cx, cy, z0), App.Vector(0, 0, 1))
        for cx, cy in dogbone_centers(x0, x1, y0, y1, radius, p, open_side)
    ]
    return fuse_slot_components(base, circles, "rasgo XY")


def integrated_slot_xz(x0, x1, z0, z1, y0, depth, p, open_side=None):
    base = Part.makeBox(x1 - x0, depth, z1 - z0, App.Vector(x0, y0, z0))
    if not dogbone_enabled(p):
        return base
    radius = dogbone_radius(p)
    circles = [
        Part.makeCylinder(radius, depth, App.Vector(cx, y0, cz), App.Vector(0, 1, 0))
        for cx, cz in dogbone_centers(x0, x1, z0, z1, radius, p, open_side)
    ]
    return fuse_slot_components(base, circles, "rasgo XZ")


def integrated_slot_yz(y0, y1, z0, z1, x0, depth, p, open_side=None):
    base = Part.makeBox(depth, y1 - y0, z1 - z0, App.Vector(x0, y0, z0))
    if not dogbone_enabled(p):
        return base
    radius = dogbone_radius(p)
    circles = [
        Part.makeCylinder(radius, depth, App.Vector(x0, cy, cz), App.Vector(1, 0, 0))
        for cy, cz in dogbone_centers(y0, y1, z0, z1, radius, p, open_side)
    ]
    return fuse_slot_components(base, circles, "rasgo YZ")



def male_tab_root_reliefs_frame(ranges, root_z, y0, thickness, p):
    """Alívios T-bone nas raízes dos dentes macho do quadro (plano XZ)."""
    if not dogbone_enabled(p):
        return []
    radius = dogbone_radius(p)
    overlap = max(0.20, radius * 0.22)
    offset = max(radius * 0.35, radius - overlap)
    extra = 0.8
    cutters = []
    for a, b in ranges:
        # O dente cresce em Z; o alívio correto fica deitado no eixo X.
        for x in (a - offset, b + offset):
            cutters.append(
                Part.makeCylinder(
                    radius,
                    thickness + 2.0 * extra,
                    App.Vector(x, y0 - extra, root_z),
                    App.Vector(0, 1, 0),
                )
            )
    return cutters


def male_tab_root_reliefs_leg(ranges, root_x, y0, thickness, p):
    """Alívios T-bone nas raízes dos dentes macho frontal/traseiro da perna."""
    if not dogbone_enabled(p):
        return []
    radius = dogbone_radius(p)
    overlap = max(0.20, radius * 0.22)
    offset = max(radius * 0.35, radius - overlap)
    extra = 0.8
    cutters = []
    for a, b in ranges:
        # O dente cresce em X; o alívio correto acompanha Z, acima/abaixo da aba.
        for z in (a - offset, b + offset):
            cutters.append(
                Part.makeCylinder(
                    radius,
                    thickness + 2.0 * extra,
                    App.Vector(root_x, y0 - extra, z),
                    App.Vector(0, 1, 0),
                )
            )
    return cutters



def male_tab_root_reliefs_leg_cap(p, z0, width, depth, thickness):
    """
    Alívios nas oito famílias de cantos côncavos das tampas dentadas.

    A tampa está no plano XY. Os dentes que avançam em Y recebem alívio
    lateral em X; os dentes que avançam em X recebem alívio lateral em Y.
    Isso evita os cantos retos observados nas peças em formato de cruz.
    """
    if not (dogbone_enabled(p) and leg_cap_joint_enabled(p)):
        return []

    cap_x0 = p["wall"] + p["cap_internal_clearance"]
    cap_y0 = p["wall"] + p["cap_internal_clearance"]
    cap_w = width - 2.0 * cap_x0
    cap_d = depth - 2.0 * cap_y0

    radius = dogbone_radius(p)
    overlap = max(0.20, radius * 0.22)
    offset = max(radius * 0.35, radius - overlap)
    extra = 0.8
    cutters = []

    # Dentes das bordas frontal e traseira: largura no eixo X.
    for a, b in cap_tooth_ranges(cap_x0, cap_w, p):
        for root_y in (cap_y0, cap_y0 + cap_d):
            for x in (a - offset, b + offset):
                cutters.append(
                    Part.makeCylinder(
                        radius,
                        thickness + 2.0 * extra,
                        App.Vector(x, root_y, z0 - extra),
                        App.Vector(0, 0, 1),
                    )
                )

    # Dentes das bordas esquerda e direita: largura no eixo Y.
    for a, b in cap_tooth_ranges(cap_y0, cap_d, p):
        for root_x in (cap_x0, cap_x0 + cap_w):
            for y in (a - offset, b + offset):
                cutters.append(
                    Part.makeCylinder(
                        radius,
                        thickness + 2.0 * extra,
                        App.Vector(root_x, y, z0 - extra),
                        App.Vector(0, 0, 1),
                    )
                )

    return cutters


def male_tab_root_reliefs_cap_rib(
    descriptor, p, x0, y0, z0, width, depth, thickness
):
    """Alívios nas raízes dos dentes adicionais da tampa-costela."""
    if not (dogbone_enabled(p) and tampa_costela_enabled(p)):
        return []

    mode = p["cap_rib_sides"]
    if mode == "Automático":
        side_count = 2 if descriptor["kind"] == "axis_corner" else 1
    elif mode == "2 lados internos":
        side_count = 2
    else:
        side_count = 1

    radius = dogbone_radius(p)
    overlap = max(0.20, radius * 0.22)
    offset = max(radius * 0.35, radius - overlap)
    extra = 0.8
    cutters = []

    # Dentes no lado +Y; as raízes recebem alívio lateral em X.
    root_y = y0 + depth
    for a, b in distributed_ranges(
        x0, width, p["rib_tab_count"], p["rib_tab_width"]
    ):
        for x in (a - offset, b + offset):
            cutters.append(
                Part.makeCylinder(
                    radius,
                    thickness + 2.0 * extra,
                    App.Vector(x, root_y, z0 - extra),
                    App.Vector(0, 0, 1),
                )
            )

    # Segundo lado interno no +X; alívio lateral em Y.
    if side_count >= 2:
        root_x = x0 + width
        for a, b in distributed_ranges(
            y0, depth, p["rib_tab_count"], p["rib_tab_width"]
        ):
            for y in (a - offset, b + offset):
                cutters.append(
                    Part.makeCylinder(
                        radius,
                        thickness + 2.0 * extra,
                        App.Vector(root_x, y, z0 - extra),
                        App.Vector(0, 0, 1),
                    )
                )

    return cutters

def male_tab_root_reliefs_rib_planar(center, p, deep_down=False, rib_height_override=None):
    """T-bone local nas raízes côncavas dos dentes das costelas planares."""
    if not (dogbone_enabled(p) and costela_encaixe_enabled(p)):
        return []

    rib_width, rib_height = rib_dimensions(p)
    if rib_height_override is not None:
        rib_height = rib_height_override
    x0 = center - p["rib_thickness"] / 2.0
    y0 = p["wall"] + p["rib_clearance"]
    z0 = p["wall"] + p["rib_clearance"]
    radius = dogbone_radius(p)
    overlap = max(0.20, radius * 0.22)
    offset = max(radius * 0.35, radius - overlap)
    extra = 0.8
    cutters = []
    sides = selected_rib_sides(p)

    for side in sides:
        if side in ("outer", "inner"):
            root_y = y0 if side == "outer" else y0 + rib_width
            center_y = root_y + offset if side == "outer" else root_y - offset
            for a, b in distributed_ranges(
                z0, rib_height, p["rib_tab_count"], p["rib_tab_width"]
            ):
                for z in (a, b):
                    cutters.append(Part.makeCylinder(
                        radius,
                        p["rib_thickness"] + 2.0 * extra,
                        App.Vector(x0 - extra, center_y, z),
                        App.Vector(1, 0, 0),
                    ))
        else:
            if deep_down and side == "upper":
                continue
            root_z = z0 if side == "lower" else z0 + rib_height
            center_z = root_z + offset if side == "lower" else root_z - offset
            for a, b in distributed_ranges(
                y0, rib_width, p["rib_tab_count"], p["rib_tab_width"]
            ):
                for y in (a, b):
                    cutters.append(Part.makeCylinder(
                        radius,
                        p["rib_thickness"] + 2.0 * extra,
                        App.Vector(x0 - extra, y, center_z),
                        App.Vector(1, 0, 0),
                    ))

    if deep_down:
        tooth_w = min(
            max(p["rib_tab_width"], p["rib_thickness"] * 2.0),
            rib_width * 0.70,
        )
        a = y0 + (rib_width - tooth_w) / 2.0
        b = a + tooth_w
        center_z = z0 + rib_height - offset
        for y in (a, b):
            cutters.append(Part.makeCylinder(
                radius,
                p["rib_thickness"] + 2.0 * extra,
                App.Vector(x0 - extra, y, center_z),
                App.Vector(1, 0, 0),
            ))

    return cutters


def male_tab_root_reliefs_rib_axis(center, p, centered, width=None, height=None):
    """T-bone local nas raízes côncavas dos dentes das costelas 3D."""
    if not (dogbone_enabled(p) and costela_encaixe_enabled(p)):
        return []

    if width is None or height is None:
        width, height = rib_dimensions(p)
    if centered:
        x0 = -width / 2.0
        y0 = -height / 2.0
    else:
        x0 = p["wall"] + p["rib_clearance"]
        y0 = p["wall"] + p["rib_clearance"]
    z0 = center - p["rib_thickness"] / 2.0
    radius = dogbone_radius(p)
    overlap = max(0.20, radius * 0.22)
    offset = max(radius * 0.35, radius - overlap)
    extra = 0.8
    cutters = []

    for side in selected_rib_sides(p):
        if side in ("outer", "inner"):
            root_x = x0 if side == "outer" else x0 + width
            center_x = root_x + offset if side == "outer" else root_x - offset
            for a, b in distributed_ranges(
                y0, height, p["rib_tab_count"], p["rib_tab_width"]
            ):
                for y in (a, b):
                    cutters.append(Part.makeCylinder(
                        radius,
                        p["rib_thickness"] + 2.0 * extra,
                        App.Vector(center_x, y, z0 - extra),
                        App.Vector(0, 0, 1),
                    ))
        else:
            root_y = y0 if side == "lower" else y0 + height
            center_y = root_y + offset if side == "lower" else root_y - offset
            for a, b in distributed_ranges(
                x0, width, p["rib_tab_count"], p["rib_tab_width"]
            ):
                for x in (a, b):
                    cutters.append(Part.makeCylinder(
                        radius,
                        p["rib_thickness"] + 2.0 * extra,
                        App.Vector(x, center_y, z0 - extra),
                        App.Vector(0, 0, 1),
                    ))

    return cutters


def planar_slot_cutters(descriptor, p, centers, connection_centers=None):
    if not (p["real_slots"] and costela_encaixe_enabled(p)):
        return {"outer": [], "inner": [], "lower": [], "upper": []}
    width = p["profile_width"]
    height = p["profile_height"]
    wall = p["wall"]
    rib_width, regular_rib_height = rib_dimensions(p)
    y0 = wall + p["rib_clearance"]
    z0 = wall + p["rib_clearance"]
    clearance = p["rib_slot_clearance"]
    depth_extra = 1.0
    result = {"outer": [], "inner": [], "lower": [], "upper": []}
    sides = selected_rib_sides(p)
    connection_set = {round(float(value), 6) for value in (connection_centers or [])}
    for center in centers:
        is_connection = round(float(center), 6) in connection_set
        rib_height = regular_rib_height
        if is_connection and p.get("t_rib_respects_toco", True):
            rib_height = min(regular_rib_height, max(TOL, connection_rib_bottom_limit(p) - z0))
        x0 = center - p["rib_thickness"] / 2.0 - clearance
        xsize = p["rib_thickness"] + 2.0 * clearance
        for side in sides:
            if side in ("outer", "inner"):
                for a, b in distributed_ranges(z0, rib_height, p["rib_tab_count"], p["rib_tab_width"]):
                    y = -depth_extra if side == "outer" else width - wall - depth_extra
                    result[side].append(integrated_slot_xz(
                        x0, x0 + xsize, a - clearance, b + clearance,
                        y, wall + 2.0 * depth_extra, p
                    ))
            else:
                if is_connection and side == "upper" and p.get("t_rib_respects_toco", True):
                    continue
                for a, b in distributed_ranges(y0, rib_width, p["rib_tab_count"], p["rib_tab_width"]):
                    z = -depth_extra if side == "lower" else height - wall - depth_extra
                    result[side].append(integrated_slot_xy(
                        x0, x0 + xsize, a - clearance, b + clearance,
                        z, wall + 2.0 * depth_extra, p
                    ))
    return result


def axis_slot_cutters(descriptor, p, centers, width, depth):
    if not (p["real_slots"] and costela_encaixe_enabled(p)):
        return {"outer": [], "inner": [], "lower": [], "upper": []}
    wall = p["wall"]
    centered = descriptor["kind"] == "axis_center"
    rib_width, rib_height = rib_dimensions(p)
    if centered:
        x0 = -width / 2.0
        y0 = -depth / 2.0
        core_x = -rib_width / 2.0
        core_y = -rib_height / 2.0
    else:
        x0 = 0.0
        y0 = 0.0
        core_x = wall + p["rib_clearance"]
        core_y = wall + p["rib_clearance"]
    clearance = p["rib_slot_clearance"]
    extra = 1.0
    result = {"outer": [], "inner": [], "lower": [], "upper": []}
    sides = selected_rib_sides(p)

    for center in centers:
        z0 = center - p["rib_thickness"] / 2.0 - clearance
        zsize = p["rib_thickness"] + 2.0 * clearance
        for side in sides:
            if side in ("outer", "inner"):
                ranges = distributed_ranges(core_y, rib_height, p["rib_tab_count"], p["rib_tab_width"])
                for a, b in ranges:
                    a -= clearance
                    b += clearance
                    x = x0 - extra if side == "outer" else x0 + width - wall - extra
                    result[side].append(integrated_slot_yz(
                        a, b, z0, z0 + zsize, x, wall + 2.0 * extra, p
                    ))
            else:
                ranges = distributed_ranges(core_x, rib_width, p["rib_tab_count"], p["rib_tab_width"])
                for a, b in ranges:
                    a -= clearance
                    b += clearance
                    y = y0 - extra if side == "lower" else y0 + depth - wall - extra
                    result[side].append(integrated_slot_xz(
                        a, b, z0, z0 + zsize, y, wall + 2.0 * extra, p
                    ))
    return result


def cap_rib_slot_cutters_axis(descriptor, p, z_start, width, depth):
    """
    Rasgos fêmea correspondentes aos dentes da tampa-costela da perna.

    A tampa interna pode ter um lado dentado em uma perna intermediária
    e dois lados em uma perna de canto. Esses dentes agora sempre possuem
    os rasgos correspondentes nas paredes da perna.
    """
    result = {"outer": [], "inner": [], "lower": [], "upper": []}
    if not (
        p.get("real_slots", False)
        and tampa_costela_enabled(p)
        and descriptor.get("kind") in ("axis_corner", "axis_edge")
    ):
        return result

    mode = p["cap_rib_sides"]
    if mode == "Automático":
        side_count = 2 if descriptor["kind"] == "axis_corner" else 1
    elif mode == "2 lados internos":
        side_count = 2
    else:
        side_count = 1

    cap_w, cap_d, cap_x0, cap_y0 = internal_cap_dimensions(p)
    cap_t = cap_thickness(p)
    clearance = p["rib_slot_clearance"]
    extra = 0.8

    # Dentes do lado +Y entram na parede traseira da perna.
    for a, b in distributed_ranges(
        cap_x0, cap_w, p["rib_tab_count"], p["rib_tab_width"]
    ):
        result["upper"].append(
            integrated_slot_xz(
                a - clearance,
                b + clearance,
                z_start - clearance,
                z_start + cap_t + clearance,
                depth - p["wall"] - extra,
                p["wall"] + 2.0 * extra,
                p,
            )
        )

    # Em perna de canto, os dentes do lado +X entram na parede direita.
    if side_count >= 2:
        for a, b in distributed_ranges(
            cap_y0, cap_d, p["rib_tab_count"], p["rib_tab_width"]
        ):
            result["inner"].append(
                integrated_slot_yz(
                    a - clearance,
                    b + clearance,
                    z_start - clearance,
                    z_start + cap_t + clearance,
                    width - p["wall"] - extra,
                    p["wall"] + 2.0 * extra,
                    p,
                )
            )

    return result


def safe_fuse_shapes(shapes, context):
    shapes = [shape for shape in shapes if shape is not None and not shape.isNull()]
    if not shapes:
        raise ValueError("Nenhuma geometria válida para {}.".format(context))
    if len(shapes) == 1:
        return shapes[0]
    result = shapes[0]
    try:
        for shape in shapes[1:]:
            result = result.fuse(shape)
        result = result.removeSplitter()
        if result.isNull():
            raise ValueError("resultado nulo")
        return result
    except Exception as exc:
        App.Console.PrintWarning(
            "Não foi possível unir completamente {}: {}. Mantido como composto seguro.\n".format(
                context, exc
            )
        )
        return Part.makeCompound(shapes)


def adaptive_tooth_ranges(intervals, nominal_tooth, gap, minimum_tooth, edge_pad=0.0):
    """Distribui dentes em cada vão livre; em vãos curtos cria um dente reduzido central."""
    result = []
    for raw_a, raw_b in intervals:
        a = raw_a + edge_pad
        b = raw_b - edge_pad
        available = b - a
        if available < minimum_tooth - TOL:
            continue

        if nominal_tooth > available + TOL:
            reduced = min(nominal_tooth, available)
            start = a + (available - reduced) / 2.0
            result.append((start, start + reduced))
            continue

        if gap <= TOL:
            count = max(1, int(math.floor(available / nominal_tooth)))
            total = count * nominal_tooth
        else:
            count = max(1, int(math.floor((available + gap) / (nominal_tooth + gap))))
            total = count * nominal_tooth + max(0, count - 1) * gap
            while count > 1 and total > available + TOL:
                count -= 1
                total = count * nominal_tooth + max(0, count - 1) * gap

        if total > available + TOL:
            reduced = min(nominal_tooth, available)
            start = a + (available - reduced) / 2.0
            result.append((start, start + reduced))
            continue

        cursor = a + (available - total) / 2.0
        for _index in range(count):
            result.append((cursor, cursor + nominal_tooth))
            cursor += nominal_tooth + gap
    return result


def frame_safe_interval(descriptor, p):
    length = descriptor["length"]
    footprint = descriptor["footprint"]
    start_inner_x = footprint[3][0]
    end_inner_x = footprint[2][0]
    margin = p["frame_tooth_margin"]
    return (
        max(0.0, start_inner_x) + margin,
        min(length, end_inner_x) - margin,
    )


def frame_tooth_ranges(descriptor, p):
    if not frame_joint_enabled(p):
        return []

    safe_start, safe_end = frame_safe_interval(descriptor, p)
    available = safe_end - safe_start
    if available <= TOL:
        App.Console.PrintWarning(
            "Segmento {:.2f} mm sem faixa útil depois das meias-esquadrias.\n".format(
                descriptor["length"]
            )
        )
        return []

    nominal = p["frame_tooth_length"]
    minimum = min(nominal, max(p["wall"] * 1.5, nominal * 0.30))
    return adaptive_tooth_ranges(
        [(safe_start, safe_end)], nominal, p["frame_tooth_gap"], minimum
    )

def frame_joint_geometry(descriptor, p):
    """
    Retorna abas das paredes e ferramentas de corte dos painéis.
    As abas ficam nas paredes externa/interna e entram nos painéis
    superior/inferior. No painel inferior, dentes que coincidiriam com
    aberturas de pernas/tocos são automaticamente removidos.
    """
    result = {
        "outer_tabs": [],
        "inner_tabs": [],
        "upper_cutters": [],
        "lower_cutters": [],
        "upper_ranges": [],
        "lower_ranges": [],
    }
    if not frame_joint_enabled(p):
        return result

    width = p["profile_width"]
    height = p["profile_height"]
    wall = p["wall"]
    depth = frame_tooth_depth(p)
    clearance = p["frame_tooth_clearance"]
    extra = 0.6

    upper_ranges = frame_tooth_ranges(descriptor, p)
    lower_openings = merge_intervals(
        list(descriptor.get("lower_openings", [])),
        0.0,
        descriptor["length"],
    )

    # A borda inferior é redistribuída dentro de cada vão livre. Antes ela
    # apenas copiava os dentes superiores e removia os que colidiam com uma
    # perna; em lados curtos isso podia apagar todos os dentes.
    safe_start, safe_end = frame_safe_interval(descriptor, p)
    safety = max(clearance, 0.20)
    blocked_ranges = [(0.0, safe_start), (safe_end, descriptor["length"])]
    blocked_ranges.extend(
        (max(0.0, a - safety), min(descriptor["length"], b + safety))
        for a, b in lower_openings
    )
    lower_free = free_intervals(
        descriptor["length"],
        merge_intervals(blocked_ranges, 0.0, descriptor["length"]),
    )
    minimum = min(
        p["frame_tooth_length"],
        max(p["wall"] * 1.5, p["frame_tooth_length"] * 0.30),
    )
    lower_ranges = adaptive_tooth_ranges(
        lower_free,
        p["frame_tooth_length"],
        p["frame_tooth_gap"],
        minimum,
        edge_pad=max(clearance, 0.35),
    )
    result["upper_ranges"] = upper_ranges
    result["lower_ranges"] = lower_ranges

    # Abas superiores e rasgos correspondentes. Cada aba é furada
    # individualmente antes da fusão, evitando perda de furos em Compounds.
    for a, b in upper_ranges:
        tab_length = b - a
        z_center = wall - depth / 2.0
        outer_tab = Part.makeBox(
            tab_length, wall, depth, App.Vector(a, 0.0, wall - depth)
        )
        inner_tab = Part.makeBox(
            tab_length, wall, depth, App.Vector(a, width - wall, wall - depth)
        )
        outer_tab = safe_cut_shape(
            outer_tab,
            frame_male_tooth_hole_cutters(p, [(a, b)], z_center, 0.0),
            "furo individual do dente superior externo",
        )
        inner_tab = safe_cut_shape(
            inner_tab,
            frame_male_tooth_hole_cutters(
                p, [(a, b)], z_center, width - wall
            ),
            "furo individual do dente superior interno",
        )
        result["outer_tabs"].append(outer_tab)
        result["inner_tabs"].append(inner_tab)
        x0 = a - clearance
        x1 = b + clearance
        result["upper_cutters"].append(
            integrated_slot_xy(
                x0, x1,
                -extra, wall + clearance,
                wall - depth - extra, depth + 2.0 * extra,
                p, open_side="v_min",
            )
        )
        result["upper_cutters"].append(
            integrated_slot_xy(
                x0, x1,
                width - wall - clearance, width + extra,
                wall - depth - extra, depth + 2.0 * extra,
                p, open_side="v_max",
            )
        )

    # Abas inferiores: não são criadas nas zonas reservadas para pernas/tocos.
    # A furação também é feita aba por aba antes da fusão.
    for a, b in lower_ranges:
        tab_length = b - a
        z_center = height - wall + depth / 2.0
        outer_tab = Part.makeBox(
            tab_length, wall, depth, App.Vector(a, 0.0, height - wall)
        )
        inner_tab = Part.makeBox(
            tab_length, wall, depth, App.Vector(a, width - wall, height - wall)
        )
        outer_tab = safe_cut_shape(
            outer_tab,
            frame_male_tooth_hole_cutters(p, [(a, b)], z_center, 0.0),
            "furo individual do dente inferior externo",
        )
        inner_tab = safe_cut_shape(
            inner_tab,
            frame_male_tooth_hole_cutters(
                p, [(a, b)], z_center, width - wall
            ),
            "furo individual do dente inferior interno",
        )
        result["outer_tabs"].append(outer_tab)
        result["inner_tabs"].append(inner_tab)
        x0 = a - clearance
        x1 = b + clearance
        result["lower_cutters"].append(
            integrated_slot_xy(
                x0, x1,
                -extra, wall + clearance,
                height - wall - extra, depth + 2.0 * extra,
                p, open_side="v_min",
            )
        )
        result["lower_cutters"].append(
            integrated_slot_xy(
                x0, x1,
                width - wall - clearance, width + extra,
                height - wall - extra, depth + 2.0 * extra,
                p, open_side="v_max",
            )
        )

    return result



def equally_spaced_centers(start, span, count):
    """Centros igualmente espaçados, com margens iguais nas extremidades."""
    if count < 1 or span <= TOL:
        return []
    spacing = span / float(count + 1)
    return [start + spacing * index for index in range(1, count + 1)]


def unique_scalar_centers(values, tolerance=1e-4):
    """Remove centros repetidos, preservando a ordem crescente."""
    result = []
    for value in sorted(float(v) for v in values):
        if not result or abs(value - result[-1]) > tolerance:
            result.append(value)
    return result


def tooth_hole_centers(a, b, p):
    """Posições dos furos ao longo de um dente, respeitando margem de borda."""
    if b - a <= TOL:
        return []
    edge = p.get("tooth_hole_edge", 0.0)
    if edge <= TOL:
        edge = p["wall"] / 2.0
    usable_a = a + edge
    usable_b = b - edge
    count = max(1, int(p.get("tooth_hole_count", 1)))
    if usable_b - usable_a <= TOL:
        return [(a + b) / 2.0]
    if count == 1:
        return [(usable_a + usable_b) / 2.0]
    return equally_spaced_centers(usable_a, usable_b - usable_a, count)


def frame_male_tooth_hole_cutters(p, ranges, z_center, y_start):
    """Furos reais nos dentes macho das paredes externa/interna do quadro."""
    if not p.get("tooth_holes_frame", False):
        return []
    radius = p["tooth_hole_diameter"] / 2.0
    over = max(2.0, radius * 0.75)
    cutters = []
    for a, b in ranges:
        for x_center in tooth_hole_centers(a, b, p):
            cutters.append(Part.makeCylinder(
                radius,
                p["wall"] + 2.0 * over,
                App.Vector(x_center, y_start - over, z_center),
                App.Vector(0, 1, 0),
            ))
    return cutters


def leg_male_tooth_hole_cutters(p, ranges, x_positions, y_start):
    """Furos reais nos dentes macho dos painéis frontal/traseiro das pernas."""
    if not p.get("tooth_holes_leg", False):
        return []
    radius = p["tooth_hole_diameter"] / 2.0
    over = max(2.0, radius * 0.75)
    cutters = []
    for a, b in ranges:
        for z_center in tooth_hole_centers(a, b, p):
            for x_center in x_positions:
                cutters.append(Part.makeCylinder(
                    radius,
                    p["wall"] + 2.0 * over,
                    App.Vector(x_center, y_start - over, z_center),
                    App.Vector(0, 1, 0),
                ))
    return cutters


def cap_male_tooth_hole_cutters(p, z0, width, depth, thickness):
    """Furos reais nos dentes macho das tampas superior/inferior."""
    if not (p.get("tooth_holes_cap", False) and leg_cap_joint_enabled(p)):
        return []
    radius = p["tooth_hole_diameter"] / 2.0
    over = max(2.0, radius * 0.75)
    _cw, _cd, cap_x0, cap_y0 = internal_cap_dimensions(p)
    cap_w = width - 2.0 * cap_x0
    cap_d = depth - 2.0 * cap_y0
    cutters = []

    # Dentes nas bordas frontal/traseira; furos distribuídos no eixo X.
    for a, b in cap_tooth_ranges(cap_x0, cap_w, p):
        for x_center in tooth_hole_centers(a, b, p):
            for y_center in (cap_y0 / 2.0, (cap_y0 + cap_d + depth) / 2.0):
                cutters.append(Part.makeCylinder(
                    radius, thickness + 2.0 * over,
                    App.Vector(x_center, y_center, z0 - over),
                    App.Vector(0, 0, 1),
                ))

    # Dentes nas bordas esquerda/direita; furos distribuídos no eixo Y.
    for a, b in cap_tooth_ranges(cap_y0, cap_d, p):
        for y_center in tooth_hole_centers(a, b, p):
            for x_center in (cap_x0 / 2.0, (cap_x0 + cap_w + width) / 2.0):
                cutters.append(Part.makeCylinder(
                    radius, thickness + 2.0 * over,
                    App.Vector(x_center, y_center, z0 - over),
                    App.Vector(0, 0, 1),
                ))
    return cutters


def leg_cap_receiver_tooth_hole_cutters(p, z_start, tube_length, width, depth, x0=0.0, y0=0.0):
    """
    Furos reais nas peças receptoras dos dentes das tampas.

    lower/upper = painéis frontal/traseiro da perna
    outer/inner = painéis esquerdo/direito da perna
    """
    result = {"lower": [], "upper": [], "outer": [], "inner": []}
    if not (
        p.get("tooth_holes_cap", False)
        and p.get("tooth_holes_receivers", True)
        and leg_cap_joint_enabled(p)
    ):
        return result

    radius = p["tooth_hole_diameter"] / 2.0
    over = max(2.0, radius * 0.75)
    wall = p["wall"]
    cap_t = cap_thickness(p)

    cap_x0 = wall + p["cap_internal_clearance"]
    cap_y0 = wall + p["cap_internal_clearance"]
    cap_w = width - 2.0 * cap_x0
    cap_d = depth - 2.0 * cap_y0

    cap_levels = []
    if upper_cap_enabled(p):
        cap_levels.append(z_start + cap_recess(p))
    if lower_cap_enabled(p):
        cap_levels.append(lower_cap_z(p, z_start + tube_length, cap_t))

    for cap_z in cap_levels:
        z_center = cap_z + cap_t / 2.0

        # Dentes das bordas frontal/traseira da tampa -> furos nos painéis frontal/traseiro.
        for a, b in cap_tooth_ranges(cap_x0, cap_w, p):
            for x_center in tooth_hole_centers(a, b, p):
                result["lower"].append(Part.makeCylinder(
                    radius, wall + 2.0 * over,
                    App.Vector(x_center, y0 - over, z_center),
                    App.Vector(0, 1, 0),
                ))
                result["upper"].append(Part.makeCylinder(
                    radius, wall + 2.0 * over,
                    App.Vector(x_center, y0 + depth - wall - over, z_center),
                    App.Vector(0, 1, 0),
                ))

        # Dentes das bordas esquerda/direita da tampa -> furos nos painéis esquerdo/direito.
        for a, b in cap_tooth_ranges(cap_y0, cap_d, p):
            for y_center in tooth_hole_centers(a, b, p):
                result["outer"].append(Part.makeCylinder(
                    radius, wall + 2.0 * over,
                    App.Vector(x0 - over, y_center, z_center),
                    App.Vector(1, 0, 0),
                ))
                result["inner"].append(Part.makeCylinder(
                    radius, wall + 2.0 * over,
                    App.Vector(x0 + width - wall - over, y_center, z_center),
                    App.Vector(1, 0, 0),
                ))

    return result


def frame_receiver_tooth_hole_cutters(p, upper_ranges, lower_ranges, width, height):
    """Furos nas chapas superior/inferior alinhados aos dentes das paredes."""
    result = {"upper": [], "lower": []}
    if not (p.get("tooth_holes_frame", False) and p.get("tooth_holes_receivers", True)):
        return result
    radius = p["tooth_hole_diameter"] / 2.0
    over = max(2.0, radius * 0.75)
    y_positions = (p["wall"] / 2.0, width - p["wall"] / 2.0)
    for ranges, key, z in ((upper_ranges, "upper", -over), (lower_ranges, "lower", height - p["wall"] - over)):
        for a, b in ranges:
            for x_center in tooth_hole_centers(a, b, p):
                for y_center in y_positions:
                    result[key].append(Part.makeCylinder(
                        radius, p["wall"] + 2.0 * over, App.Vector(x_center, y_center, z), App.Vector(0, 0, 1)
                    ))
    return result


def leg_receiver_tooth_hole_cutters(p, ranges, x0, y0, width, depth):
    """Furos nas laterais da perna alinhados aos dentes frontal/traseiro."""
    result = {"left": [], "right": []}
    if not (p.get("tooth_holes_leg", False) and p.get("tooth_holes_receivers", True)):
        return result
    radius = p["tooth_hole_diameter"] / 2.0
    over = max(2.0, radius * 0.75)
    y_positions = (y0 + p["wall"] / 2.0, y0 + depth - p["wall"] / 2.0)
    for a, b in ranges:
        for z_center in tooth_hole_centers(a, b, p):
            for y_center in y_positions:
                result["left"].append(Part.makeCylinder(
                    radius, p["wall"] + 2.0 * over, App.Vector(x0 - over, y_center, z_center), App.Vector(1, 0, 0)
                ))
                result["right"].append(Part.makeCylinder(
                    radius, p["wall"] + 2.0 * over, App.Vector(x0 + width - p["wall"] - over, y_center, z_center), App.Vector(1, 0, 0)
                ))
    return result


def leveler_cutters(p, z0, width, depth, thickness):
    """Furo central e rebaixo opcional na tampa inferior da perna."""
    if not p.get("prepare_leveler", False):
        return []
    cx = width / 2.0
    cy = depth / 2.0
    over = 0.8
    cutters = [
        Part.makeCylinder(
            p["leveler_hole_diameter"] / 2.0,
            thickness + 2.0 * over,
            App.Vector(cx, cy, z0 - over),
            App.Vector(0, 0, 1),
        )
    ]
    if p.get("leveler_counterbore", False):
        depth_value = min(p["leveler_counterbore_depth"], thickness - TOL)
        cutters.append(Part.makeCylinder(
            p["leveler_counterbore_diameter"] / 2.0,
            depth_value + over,
            App.Vector(cx, cy, z0 + thickness - depth_value),
            App.Vector(0, 0, 1),
        ))
    return cutters


def planar_rib_hole_cutters(descriptor, p, rib_centers):
    """
    Furos passantes reais nas quatro paredes do quadro para prender cada costela.

    Eixos locais do quadro:
      X = comprimento da travessa;
      Y = largura do tubo;
      Z = altura do tubo.

    Para cada costela são criados furos em:
      - parede externa e interna, distribuídos na altura;
      - painel superior e inferior, distribuídos na largura.
    """
    result = {"upper": [], "lower": [], "outer": [], "inner": []}
    if not (
        costela_parafuso_enabled(p)
        and p.get("real_rib_holes", False)
        and rib_centers
    ):
        return result

    width = p["profile_width"]
    height = p["profile_height"]
    wall = p["wall"]
    radius = p["rib_hole_diameter"] / 2.0
    over = max(0.6, radius * 0.20)

    rib_width, rib_height = rib_dimensions(p)
    y_start = wall + p["rib_clearance"]
    z_start = wall + p["rib_clearance"]
    y_positions = equally_spaced_centers(y_start, rib_width, p["rib_hole_count"])
    z_positions = equally_spaced_centers(z_start, rib_height, p["rib_hole_count"])

    for center in rib_centers:
        # Painel superior (Z mínimo) e inferior (Z máximo).
        for y_pos in y_positions:
            result["upper"].append(Part.makeCylinder(
                radius, wall + 2.0 * over,
                App.Vector(center, y_pos, -over), App.Vector(0, 0, 1)
            ))
            result["lower"].append(Part.makeCylinder(
                radius, wall + 2.0 * over,
                App.Vector(center, y_pos, height - wall - over), App.Vector(0, 0, 1)
            ))

        # Parede externa (Y mínimo) e interna (Y máximo).
        for z_pos in z_positions:
            result["outer"].append(Part.makeCylinder(
                radius, wall + 2.0 * over,
                App.Vector(center, -over, z_pos), App.Vector(0, 1, 0)
            ))
            result["inner"].append(Part.makeCylinder(
                radius, wall + 2.0 * over,
                App.Vector(center, width - wall - over, z_pos), App.Vector(0, 1, 0)
            ))

    return result


def axis_rib_hole_cutters(descriptor, p, rib_centers, width, depth):
    """Furos reais nas quatro paredes de pernas/barras para prender costelas 3D."""
    result = {"lower": [], "upper": [], "outer": [], "inner": []}
    if not (
        costela_parafuso_enabled(p)
        and p.get("real_rib_holes", False)
        and rib_centers
    ):
        return result

    wall = p["wall"]
    radius = p["rib_hole_diameter"] / 2.0
    over = max(0.6, radius * 0.20)
    centered = descriptor["kind"] == "axis_center"
    x0 = -width / 2.0 if centered else 0.0
    y0 = -depth / 2.0 if centered else 0.0

    usable_x_start = x0 + wall + p["rib_clearance"]
    usable_x_span = width - 2.0 * wall - 2.0 * p["rib_clearance"]
    usable_y_start = y0 + wall + p["rib_clearance"]
    usable_y_span = depth - 2.0 * wall - 2.0 * p["rib_clearance"]
    x_positions = equally_spaced_centers(
        usable_x_start, usable_x_span, p["rib_hole_count"]
    )
    y_positions = equally_spaced_centers(
        usable_y_start, usable_y_span, p["rib_hole_count"]
    )

    for center in rib_centers:
        # Painéis frontal/traseiro: eixo de furação em Y.
        for x_pos in x_positions:
            result["lower"].append(Part.makeCylinder(
                radius, wall + 2.0 * over,
                App.Vector(x_pos, y0 - over, center), App.Vector(0, 1, 0)
            ))
            result["upper"].append(Part.makeCylinder(
                radius, wall + 2.0 * over,
                App.Vector(x_pos, y0 + depth - wall - over, center), App.Vector(0, 1, 0)
            ))

        # Painéis esquerdo/direito: eixo de furação em X.
        for y_pos in y_positions:
            result["outer"].append(Part.makeCylinder(
                radius, wall + 2.0 * over,
                App.Vector(x0 - over, y_pos, center), App.Vector(1, 0, 0)
            ))
            result["inner"].append(Part.makeCylinder(
                radius, wall + 2.0 * over,
                App.Vector(x0 + width - wall - over, y_pos, center), App.Vector(1, 0, 0)
            ))

    return result


def make_planar_tube_parts(descriptor, p):
    length = descriptor["length"]
    width = p["profile_width"]
    height = p["profile_height"]
    wall = p["wall"]
    footprint = descriptor["footprint"]
    start_inner_x = footprint[3][0]
    end_inner_x = footprint[2][0]

    # V4.24 — MODO SEGURO DA TRAVESSA INTERNA
    #
    # O OCC estava fechando o FreeCAD ao executar dezenas de cortes/fusões
    # sobre uma peça recém-detectada. Para a travessa interna, primeiro
    # geramos as quatro chapas físicas simples, sem dentes, rasgos, furos,
    # dogbones ou costelas. Assim confirmamos leitura e posicionamento sem
    # entrar em operações C++ que podem derrubar o processo inteiro.
    if descriptor.get("internal_member", False):
        upper_panel = face_from_polygon_2d(
            footprint, 0.0
        ).extrude(App.Vector(0, 0, wall))
        lower_panel = face_from_polygon_2d(
            footprint, height - wall
        ).extrude(App.Vector(0, 0, wall))

        sw = x_at_depth(0.0, start_inner_x, wall, width)
        ew = x_at_depth(length, end_inner_x, wall, width)
        outer_strip = [
            (0.0, 0.0), (length, 0.0), (ew, wall), (sw, wall)
        ]
        outer_wall = face_from_polygon_2d(
            outer_strip, wall
        ).extrude(App.Vector(0, 0, height - 2.0 * wall))

        y0 = width - wall
        sy0 = x_at_depth(0.0, start_inner_x, y0, width)
        ey0 = x_at_depth(length, end_inner_x, y0, width)
        inner_strip = [
            (sy0, y0), (ey0, y0),
            (end_inner_x, width), (start_inner_x, width)
        ]
        inner_wall = face_from_polygon_2d(
            inner_strip, wall
        ).extrude(App.Vector(0, 0, height - 2.0 * wall))

        App.Console.PrintMessage(
            "V4.27: travessa interna {:02d} criada em modo seguro, sem booleanas pesadas.\n".format(
                descriptor.get("index", 0)
            )
        )
        return {
            "upper": upper_panel,
            "lower": [lower_panel],
            "outer": outer_wall,
            "inner": inner_wall,
            "tooth_ranges": [],
            "tooth_count": 0,
        }

    openings = list(descriptor.get("lower_openings", []))
    if descriptor.get("trim_lower_start", False):
        openings.append((0.0, start_inner_x))
    if descriptor.get("trim_lower_end", False):
        openings.append((end_inner_x, length))
    openings = merge_intervals(openings, 0.0, length)

    if descriptor.get("suppress_regular_ribs", False):
        rib_centers = []
    else:
        rib_centers = calculate_rib_centers(
            length, p, descriptor.get("rib_blocked_intervals", [])
        )
    connection_centers = unique_scalar_centers(
        descriptor.get("connection_rib_centers", [])
    )
    hug_centers = unique_scalar_centers(
        descriptor.get("local_hug_rib_centers", [])
    )
    reserved = connection_centers + hug_centers
    rib_centers = [
        c for c in unique_scalar_centers(rib_centers)
        if all(abs(c - r) > p["rib_thickness"] * 0.75 for r in reserved)
    ]
    all_slot_centers = unique_scalar_centers(
        rib_centers + connection_centers + hug_centers
    )
    slot_cutters = planar_slot_cutters(
        descriptor, p, all_slot_centers, connection_centers
    )
    hole_cutters = planar_rib_hole_cutters(descriptor, p, all_slot_centers)
    frame_joint = frame_joint_geometry(descriptor, p)
    receiver_tooth_holes = frame_receiver_tooth_hole_cutters(
        p, frame_joint["upper_ranges"], frame_joint["lower_ranges"], width, height
    )

    upper_panel = face_from_polygon_2d(footprint, 0.0).extrude(App.Vector(0, 0, wall))
    upper_panel = safe_cut_shape(
        upper_panel,
        slot_cutters["lower"] + frame_joint["upper_cutters"] + hole_cutters["upper"] + receiver_tooth_holes["upper"],
        "painel superior com furos reais das costelas",
    )

    lower_panels = []
    # O painel inferior é dividido em trechos para acomodar pernas/tocos.
    for a, b in free_intervals(length, openings):
        polygon = clip_polygon_x(footprint, a, b)
        if len(polygon) >= 3:
            try:
                lower_piece = face_from_polygon_2d(
                    polygon, height - wall
                ).extrude(App.Vector(0, 0, wall))
                lower_piece = safe_cut_shape(
                    lower_piece,
                    slot_cutters["upper"] + frame_joint["lower_cutters"] + hole_cutters["lower"] + receiver_tooth_holes["lower"],
                    "painel inferior com furos reais das costelas",
                )
                lower_panels.append(lower_piece)
            except Exception as exc:
                App.Console.PrintWarning(
                    "Trecho do painel inferior ignorado: {}\n".format(exc)
                )

    sw = x_at_depth(0.0, start_inner_x, wall, width)
    ew = x_at_depth(length, end_inner_x, wall, width)
    outer_strip = [(0.0, 0.0), (length, 0.0), (ew, wall), (sw, wall)]
    outer_wall_base = face_from_polygon_2d(
        outer_strip, wall
    ).extrude(App.Vector(0, 0, height - 2.0 * wall))
    outer_wall_base = safe_cut_shape(
        outer_wall_base, slot_cutters["outer"] + hole_cutters["outer"], "parede externa com furos reais das costelas"
    )
    outer_wall = safe_fuse_shapes(
        [outer_wall_base] + frame_joint["outer_tabs"],
        "parede externa dentada",
    )
    outer_root_reliefs = (
        male_tab_root_reliefs_frame(
            frame_joint["upper_ranges"], wall, 0.0, wall, p
        )
        + male_tab_root_reliefs_frame(
            frame_joint["lower_ranges"], height - wall, 0.0, wall, p
        )
    )
    outer_wall = safe_cut_shape(
        outer_wall, outer_root_reliefs,
        "raízes dos dentes da parede externa do quadro",
    )
    tooth_depth_value = frame_tooth_depth(p)
    outer_tooth_holes = (
        frame_male_tooth_hole_cutters(
            p, frame_joint["upper_ranges"],
            wall - tooth_depth_value / 2.0, 0.0
        )
        + frame_male_tooth_hole_cutters(
            p, frame_joint["lower_ranges"],
            height - wall + tooth_depth_value / 2.0, 0.0
        )
    )
    outer_wall = safe_cut_shape(
        outer_wall, outer_tooth_holes,
        "furos reais nos dentes da parede externa do quadro",
    )

    y0 = width - wall
    sy0 = x_at_depth(0.0, start_inner_x, y0, width)
    ey0 = x_at_depth(length, end_inner_x, y0, width)
    inner_strip = [(sy0, y0), (ey0, y0), (end_inner_x, width), (start_inner_x, width)]
    inner_wall_base = face_from_polygon_2d(
        inner_strip, wall
    ).extrude(App.Vector(0, 0, height - 2.0 * wall))
    inner_wall_base = safe_cut_shape(
        inner_wall_base, slot_cutters["inner"] + hole_cutters["inner"], "parede interna com furos reais das costelas"
    )
    inner_wall = safe_fuse_shapes(
        [inner_wall_base] + frame_joint["inner_tabs"],
        "parede interna dentada",
    )
    inner_root_reliefs = (
        male_tab_root_reliefs_frame(
            frame_joint["upper_ranges"], wall, width - wall, wall, p
        )
        + male_tab_root_reliefs_frame(
            frame_joint["lower_ranges"], height - wall, width - wall, wall, p
        )
    )
    inner_wall = safe_cut_shape(
        inner_wall, inner_root_reliefs,
        "raízes dos dentes da parede interna do quadro",
    )
    inner_tooth_holes = (
        frame_male_tooth_hole_cutters(
            p, frame_joint["upper_ranges"],
            wall - tooth_depth_value / 2.0, width - wall
        )
        + frame_male_tooth_hole_cutters(
            p, frame_joint["lower_ranges"],
            height - wall + tooth_depth_value / 2.0, width - wall
        )
    )
    inner_wall = safe_cut_shape(
        inner_wall, inner_tooth_holes,
        "furos reais nos dentes da parede interna do quadro",
    )

    return {
        "upper": upper_panel,
        "lower": lower_panels,
        "outer": outer_wall,
        "inner": inner_wall,
        "tooth_ranges": frame_joint["upper_ranges"],
        "tooth_count": 2 * len(frame_joint["upper_ranges"]) + 2 * len(frame_joint["lower_ranges"]),
    }


def make_planar_tube_compound(descriptor, p):
    """Compatibilidade: reúne as peças, sem fundi-las."""
    parts = make_planar_tube_parts(descriptor, p)
    solids = [parts["upper"], parts["outer"], parts["inner"]] + parts["lower"]
    return Part.makeCompound(solids)


def leg_tooth_ranges(z_start, tube_length, p):
    if not leg_joint_enabled(p):
        return []
    safe_start = z_start + p["leg_tooth_margin"]
    safe_end = z_start + tube_length - p["leg_tooth_margin"]
    nominal = p["leg_tooth_length"]
    minimum = min(nominal, max(p["wall"] * 1.5, nominal * 0.30))
    return adaptive_tooth_ranges(
        [(safe_start, safe_end)], nominal, p["leg_tooth_gap"], minimum
    )

def cap_tooth_ranges(start, span, p):
    if not leg_cap_joint_enabled(p):
        return []
    count = max(1, p["leg_cap_tooth_count"])
    nominal = p["leg_cap_tooth_width"]
    minimum = min(nominal, max(p["wall"] * 1.25, nominal * 0.35))
    gap = max(p["wall"], (span - count * nominal) / float(max(1, count - 1))) if count > 1 else 0.0
    ranges = adaptive_tooth_ranges([(start, start + span)], nominal, gap, minimum, edge_pad=p["wall"] * 0.35)
    if len(ranges) > count:
        # Mantém distribuição simétrica com a quantidade solicitada.
        step = len(ranges) / float(count)
        ranges = [ranges[min(len(ranges) - 1, int((i + 0.5) * step))] for i in range(count)]
    return ranges


def leg_cap_tab_boxes(p, z0, width, depth, thickness):
    if not leg_cap_joint_enabled(p):
        return []
    _cap_w, _cap_d, cap_x0, cap_y0 = internal_cap_dimensions(p)
    cap_w = width - 2.0 * p["wall"] - 2.0 * p["cap_internal_clearance"]
    cap_d = depth - 2.0 * p["wall"] - 2.0 * p["cap_internal_clearance"]
    boxes = []
    radius = p["tooth_hole_diameter"] / 2.0
    over = max(2.0, radius * 0.75)

    for a, b in cap_tooth_ranges(cap_x0, cap_w, p):
        front = Part.makeBox(
            b - a, cap_y0, thickness, App.Vector(a, 0.0, z0)
        )
        back = Part.makeBox(
            b - a, depth - (cap_y0 + cap_d), thickness,
            App.Vector(a, cap_y0 + cap_d, z0),
        )
        if p.get("tooth_holes_cap", False):
            front_cutters = []
            back_cutters = []
            for x_center in tooth_hole_centers(a, b, p):
                front_cutters.append(Part.makeCylinder(
                    radius, thickness + 2.0 * over,
                    App.Vector(x_center, cap_y0 / 2.0, z0 - over),
                    App.Vector(0, 0, 1),
                ))
                back_cutters.append(Part.makeCylinder(
                    radius, thickness + 2.0 * over,
                    App.Vector(
                        x_center,
                        (cap_y0 + cap_d + depth) / 2.0,
                        z0 - over,
                    ),
                    App.Vector(0, 0, 1),
                ))
            front = safe_cut_shape(
                front, front_cutters, "furos individuais da tampa frontal"
            )
            back = safe_cut_shape(
                back, back_cutters, "furos individuais da tampa traseira"
            )
        boxes.extend((front, back))

    for a, b in cap_tooth_ranges(cap_y0, cap_d, p):
        left = Part.makeBox(
            cap_x0, b - a, thickness, App.Vector(0.0, a, z0)
        )
        right = Part.makeBox(
            width - (cap_x0 + cap_w), b - a, thickness,
            App.Vector(cap_x0 + cap_w, a, z0),
        )
        if p.get("tooth_holes_cap", False):
            left_cutters = []
            right_cutters = []
            for y_center in tooth_hole_centers(a, b, p):
                left_cutters.append(Part.makeCylinder(
                    radius, thickness + 2.0 * over,
                    App.Vector(cap_x0 / 2.0, y_center, z0 - over),
                    App.Vector(0, 0, 1),
                ))
                right_cutters.append(Part.makeCylinder(
                    radius, thickness + 2.0 * over,
                    App.Vector(
                        (cap_x0 + cap_w + width) / 2.0,
                        y_center, z0 - over,
                    ),
                    App.Vector(0, 0, 1),
                ))
            left = safe_cut_shape(
                left, left_cutters, "furos individuais da tampa esquerda"
            )
            right = safe_cut_shape(
                right, right_cutters, "furos individuais da tampa direita"
            )
        boxes.extend((left, right))
    return boxes


def leg_cap_slot_cutters_axis(descriptor, p, z_start, tube_length, width, depth):
    result = {"outer": [], "inner": [], "lower": [], "upper": []}
    if not (p.get("real_slots", False) and leg_cap_joint_enabled(p)):
        return result

    cap_t = cap_thickness(p)
    clearance = p["leg_cap_tooth_clearance"]
    cap_w, cap_d, cap_x0, cap_y0 = internal_cap_dimensions(p)
    # Recalcula para dimensões manuais da perna, preservando a folga interna.
    cap_x0 = p["wall"] + p["cap_internal_clearance"]
    cap_y0 = p["wall"] + p["cap_internal_clearance"]
    cap_w = width - 2.0 * cap_x0
    cap_d = depth - 2.0 * cap_y0
    extra = 0.8

    recess = cap_recess(p)
    cap_levels = []
    if upper_cap_enabled(p):
        cap_levels.append(z_start + recess)
    if lower_cap_enabled(p):
        cap_levels.append(lower_cap_z(p, z_start + tube_length, cap_t))

    for cap_z in cap_levels:
        z0s = cap_z - clearance
        z1s = cap_z + cap_t + clearance
        for a, b in cap_tooth_ranges(cap_x0, cap_w, p):
            result["lower"].append(integrated_slot_xz(
                a - clearance, b + clearance, z0s, z1s,
                -extra, p["wall"] + 2.0 * extra, p
            ))
            result["upper"].append(integrated_slot_xz(
                a - clearance, b + clearance, z0s, z1s,
                depth - p["wall"] - extra, p["wall"] + 2.0 * extra, p
            ))
        for a, b in cap_tooth_ranges(cap_y0, cap_d, p):
            result["outer"].append(integrated_slot_yz(
                a - clearance, b + clearance, z0s, z1s,
                -extra, p["wall"] + 2.0 * extra, p
            ))
            result["inner"].append(integrated_slot_yz(
                a - clearance, b + clearance, z0s, z1s,
                width - p["wall"] - extra, p["wall"] + 2.0 * extra, p
            ))
    return result


def make_axis_tube_parts(
    descriptor,
    p,
    z_start=0.0,
    tube_length=None,
    width=None,
    depth=None,
    rib_centers=None,
):
    if tube_length is None:
        tube_length = descriptor["length"]
    if width is None:
        width = p["profile_width"]
    if depth is None:
        depth = p["profile_height"]

    wall = p["wall"]
    centered = descriptor["kind"] == "axis_center"
    if centered:
        x0 = -width / 2.0
        y0 = -depth / 2.0
    else:
        x0 = 0.0
        y0 = 0.0

    rib_centers = rib_centers or []
    slot_cutters = axis_slot_cutters(descriptor, p, rib_centers, width, depth)
    cap_slot_cutters = cap_rib_slot_cutters_axis(
        descriptor, p, z_start, width, depth
    )
    for side in ("outer", "inner", "lower", "upper"):
        slot_cutters[side].extend(cap_slot_cutters[side])
    end_cap_cutters = leg_cap_slot_cutters_axis(
        descriptor, p, z_start, tube_length, width, depth
    )
    for side in ("outer", "inner", "lower", "upper"):
        slot_cutters[side].extend(end_cap_cutters[side])
    hole_cutters = axis_rib_hole_cutters(
        descriptor, p, rib_centers, width, depth
    )
    for side in ("outer", "inner", "lower", "upper"):
        slot_cutters[side].extend(hole_cutters[side])

    cap_receiver_holes = leg_cap_receiver_tooth_hole_cutters(
        p, z_start, tube_length, width, depth, x0, y0
    )
    for side in ("outer", "inner", "lower", "upper"):
        slot_cutters[side].extend(cap_receiver_holes[side])

    if not leg_joint_enabled(p):
        front = Part.makeBox(width, wall, tube_length, App.Vector(x0, y0, z_start))
        back = Part.makeBox(width, wall, tube_length, App.Vector(x0, y0 + depth - wall, z_start))
        left = Part.makeBox(wall, depth - 2.0 * wall, tube_length, App.Vector(x0, y0 + wall, z_start))
        right = Part.makeBox(wall, depth - 2.0 * wall, tube_length, App.Vector(x0 + width - wall, y0 + wall, z_start))
        front = safe_cut_shape(front, slot_cutters["lower"], "painel frontal da perna")
        back = safe_cut_shape(back, slot_cutters["upper"], "painel traseiro da perna")
        left = safe_cut_shape(left, slot_cutters["outer"], "painel esquerdo da perna")
        right = safe_cut_shape(right, slot_cutters["inner"], "painel direito da perna")
        return {"front": front, "back": back, "left": left, "right": right, "tooth_count": 0}

    tooth_ranges = leg_tooth_ranges(z_start, tube_length, p)
    receiver_tooth_holes = leg_receiver_tooth_hole_cutters(p, tooth_ranges, x0, y0, width, depth)
    tooth_depth_value = leg_tooth_depth(p)
    clearance = p["leg_tooth_clearance"]
    extra = 0.6

    # Painéis frontal e traseiro ficam entre as laterais e recebem abas.
    front_base = Part.makeBox(width - 2.0 * wall, wall, tube_length, App.Vector(x0 + wall, y0, z_start))
    back_base = Part.makeBox(width - 2.0 * wall, wall, tube_length, App.Vector(x0 + wall, y0 + depth - wall, z_start))
    front_base = safe_cut_shape(front_base, slot_cutters["lower"], "painel frontal da perna")
    back_base = safe_cut_shape(back_base, slot_cutters["upper"], "painel traseiro da perna")

    left_base = Part.makeBox(wall, depth, tube_length, App.Vector(x0, y0, z_start))
    right_base = Part.makeBox(wall, depth, tube_length, App.Vector(x0 + width - wall, y0, z_start))
    left_cutters = list(slot_cutters["outer"])
    right_cutters = list(slot_cutters["inner"])
    front_tabs = []
    back_tabs = []

    for a, b in tooth_ranges:
        h = b - a
        # Abas das duas faces, nos dois cantos. Cada aba é furada
        # individualmente antes de entrar na fusão do painel.
        left_x = x0 + wall - tooth_depth_value / 2.0
        right_x = x0 + width - wall + tooth_depth_value / 2.0

        front_left = Part.makeBox(
            tooth_depth_value, wall, h,
            App.Vector(x0 + wall - tooth_depth_value, y0, a),
        )
        front_right = Part.makeBox(
            tooth_depth_value, wall, h,
            App.Vector(x0 + width - wall, y0, a),
        )
        back_left = Part.makeBox(
            tooth_depth_value, wall, h,
            App.Vector(x0 + wall - tooth_depth_value, y0 + depth - wall, a),
        )
        back_right = Part.makeBox(
            tooth_depth_value, wall, h,
            App.Vector(x0 + width - wall, y0 + depth - wall, a),
        )

        front_left = safe_cut_shape(
            front_left,
            leg_male_tooth_hole_cutters(p, [(a, b)], (left_x,), y0),
            "furo individual do dente frontal esquerdo",
        )
        front_right = safe_cut_shape(
            front_right,
            leg_male_tooth_hole_cutters(p, [(a, b)], (right_x,), y0),
            "furo individual do dente frontal direito",
        )
        back_left = safe_cut_shape(
            back_left,
            leg_male_tooth_hole_cutters(
                p, [(a, b)], (left_x,), y0 + depth - wall
            ),
            "furo individual do dente traseiro esquerdo",
        )
        back_right = safe_cut_shape(
            back_right,
            leg_male_tooth_hole_cutters(
                p, [(a, b)], (right_x,), y0 + depth - wall
            ),
            "furo individual do dente traseiro direito",
        )

        front_tabs.extend((front_left, front_right))
        back_tabs.extend((back_left, back_right))

        z0s = a - clearance
        z1s = b + clearance
        # Rasgos nos painéis laterais. Aqui o osso de cão é integrado ao corte.
        left_cutters.append(integrated_slot_yz(
            y0 - extra, y0 + wall + clearance,
            z0s, z1s,
            x0 - extra, wall + 2.0 * extra, p, open_side="u_min",
        ))
        left_cutters.append(integrated_slot_yz(
            y0 + depth - wall - clearance, y0 + depth + extra,
            z0s, z1s,
            x0 - extra, wall + 2.0 * extra, p, open_side="u_max",
        ))
        right_cutters.append(integrated_slot_yz(
            y0 - extra, y0 + wall + clearance,
            z0s, z1s,
            x0 + width - wall - extra, wall + 2.0 * extra, p, open_side="u_min",
        ))
        right_cutters.append(integrated_slot_yz(
            y0 + depth - wall - clearance, y0 + depth + extra,
            z0s, z1s,
            x0 + width - wall - extra, wall + 2.0 * extra, p, open_side="u_max",
        ))

    front = safe_fuse_shapes([front_base] + front_tabs, "painel frontal dentado da perna")
    back = safe_fuse_shapes([back_base] + back_tabs, "painel traseiro dentado da perna")

    front_root_reliefs = []
    back_root_reliefs = []
    for root_x in (x0 + wall, x0 + width - wall):
        front_root_reliefs.extend(
            male_tab_root_reliefs_leg(tooth_ranges, root_x, y0, wall, p)
        )
        back_root_reliefs.extend(
            male_tab_root_reliefs_leg(
                tooth_ranges, root_x, y0 + depth - wall, wall, p
            )
        )
    front = safe_cut_shape(
        front, front_root_reliefs,
        "raízes dos dentes do painel frontal da perna",
    )
    back = safe_cut_shape(
        back, back_root_reliefs,
        "raízes dos dentes do painel traseiro da perna",
    )
    tab_x_positions = (
        x0 + wall - tooth_depth_value / 2.0,
        x0 + width - wall + tooth_depth_value / 2.0,
    )
    front = safe_cut_shape(
        front,
        leg_male_tooth_hole_cutters(p, tooth_ranges, tab_x_positions, y0),
        "furos reais nos dentes do painel frontal da perna",
    )
    back = safe_cut_shape(
        back,
        leg_male_tooth_hole_cutters(
            p, tooth_ranges, tab_x_positions, y0 + depth - wall
        ),
        "furos reais nos dentes do painel traseiro da perna",
    )
    left = safe_cut_shape(
        left_base, left_cutters + receiver_tooth_holes["left"],
        "painel esquerdo dentado da perna com furos conjugados"
    )
    right = safe_cut_shape(
        right_base, right_cutters + receiver_tooth_holes["right"],
        "painel direito dentado da perna com furos conjugados"
    )
    return {
        "front": front,
        "back": back,
        "left": left,
        "right": right,
        "tooth_count": 4 * len(tooth_ranges),
    }


def make_axis_tube_compound(
    descriptor,
    p,
    z_start=0.0,
    tube_length=None,
    width=None,
    depth=None,
    rib_centers=None,
):
    parts = make_axis_tube_parts(
        descriptor, p,
        z_start=z_start,
        tube_length=tube_length,
        width=width,
        depth=depth,
        rib_centers=rib_centers,
    )
    return Part.makeCompound([
        parts["front"], parts["back"], parts["left"], parts["right"]
    ])


def create_shape_feature(doc, parent, name, label, shape, placement):
    feature = doc.addObject("Part::Feature", name)
    feature.Label = label
    mark_generated(feature)
    parent.addObject(feature)
    feature.Shape = shape
    feature.Placement = placement
    return feature


def create_hole_markers_planar(doc, parent, placement, segment_index, rib_index, center, p):
    # V4.11: removidos. Os furos agora são subtrações reais nas quatro chapas receptoras.
    return 0


def create_hole_markers_axis(doc, parent, placement, segment_index, rib_index, center, p, centered):
    # V4.11: removidos. Os furos agora são subtrações reais nas quatro chapas receptoras.
    return 0


def create_planar_rib_safe(doc, parent, placement, segment_index, rib_index, center, p):
    shape = planar_rib_shape(center, p)
    feature = create_shape_feature(
        doc, parent,
        "Costela_Segura_Planar_{:02d}_{:02d}".format(segment_index, rib_index),
        "Costela {} — segmento {:02d}/{:02d}".format(p["rib_mount"], segment_index, rib_index),
        shape, placement,
    )
    create_hole_markers_planar(doc, parent, placement, segment_index, rib_index, center, p)
    return feature


def create_connection_rib_safe(doc, parent, placement, segment_index, center, p):
    shape = planar_rib_shape(
        center, p,
        deep_down=bool(p.get("deep_lower_tooth", False)),
        bottom_limit_z=connection_rib_bottom_limit(p),
    )
    feature = create_shape_feature(
        doc, parent,
        "Costela_Conexao_T_{:02d}_{:05d}".format(segment_index, int(round(center))),
        "Costela de conexão T — segmento {:02d}".format(segment_index),
        shape, placement,
    )
    try:
        feature.ViewObject.ShapeColor = (0.82, 0.68, 0.30)
    except Exception:
        pass
    marker_index = max(900, int(round(center * 10.0)))
    create_hole_markers_planar(
        doc, parent, placement, segment_index, marker_index, center, p
    )
    return feature


def create_axis_rib_safe(doc, parent, placement, segment_index, rib_index, center, p, centered):
    shape = axis_rib_shape(center, p, centered)
    feature = create_shape_feature(
        doc, parent,
        "Costela_Segura_3D_{:02d}_{:02d}".format(segment_index, rib_index),
        "Costela 3D {} — {:02d}/{:02d}".format(p["rib_mount"], segment_index, rib_index),
        shape, placement,
    )
    create_hole_markers_axis(doc, parent, placement, segment_index, rib_index, center, p, centered)
    return feature


def create_planar_segment(doc, root, descriptor, p):
    suffix = "{:02d}".format(descriptor["index"])
    group = doc.addObject("App::Part", "Segmento_Seguro_Planar_" + suffix)
    if descriptor.get("line_member", False):
        group.Label = "Membro interno {:02d} — {:.2f} mm".format(
            descriptor["index"], descriptor["length"]
        )
    elif descriptor.get("internal_member", False):
        group.Label = "Travessa interna segura {:02d} — {:.2f} mm".format(
            descriptor["index"], descriptor["length"]
        )
    else:
        group.Label = "Quadro {:02d} — {:.2f} mm".format(
            descriptor["index"], descriptor["length"]
        )
    mark_generated(group)
    root.addObject(group)

    offset = vector_scaled(descriptor["axis_z"], p["normal_offset"])
    global_z_offset = App.Vector(0.0, 0.0, p["legacy_z"])
    origin = App.Vector(descriptor["start"]).add(offset).add(global_z_offset)
    placement = matrix_placement(origin, descriptor["axis_x"], descriptor["axis_y"], descriptor["axis_z"])

    parts = make_planar_tube_parts(descriptor, p)

    create_shape_feature(
        doc, group,
        ("Painel_Superior_Membro_" if descriptor.get("line_member", False) else "Painel_Superior_Quadro_") + suffix,
        "Painel superior — segmento " + suffix,
        parts["upper"], placement,
    )
    create_shape_feature(
        doc, group,
        ("Painel_Lateral_A_Membro_" if descriptor.get("line_member", False) else "Painel_Externo_Quadro_") + suffix,
        "Painel externo dentado — segmento " + suffix
        if frame_joint_enabled(p) else
        "Painel externo — segmento " + suffix,
        parts["outer"], placement,
    )
    create_shape_feature(
        doc, group,
        ("Painel_Lateral_B_Membro_" if descriptor.get("line_member", False) else "Painel_Interno_Quadro_") + suffix,
        "Painel interno dentado — segmento " + suffix
        if frame_joint_enabled(p) else
        "Painel interno — segmento " + suffix,
        parts["inner"], placement,
    )
    for piece_index, shape in enumerate(parts["lower"], start=1):
        create_shape_feature(
            doc, group,
            "Painel_Inferior_Quadro_{}_{:02d}".format(suffix, piece_index),
            "Painel inferior — segmento {} / trecho {:02d}".format(suffix, piece_index),
            shape, placement,
        )

    if descriptor.get("internal_member", False):
        # Modo seguro: a travessa é criada primeiro sem costelas.
        centers = []
        connection_centers = []
        hug_centers = []
    else:
        if descriptor.get("suppress_regular_ribs", False):
            centers = []
        else:
            centers = calculate_rib_centers(
                descriptor["length"], p,
                descriptor.get("rib_blocked_intervals", [])
            )
        connection_centers = unique_scalar_centers(
            descriptor.get("connection_rib_centers", [])
        )
        hug_centers = unique_scalar_centers(
            descriptor.get("local_hug_rib_centers", [])
        )
    reserved = connection_centers + hug_centers
    centers = [
        c for c in unique_scalar_centers(centers)
        if all(abs(c - r) > p["rib_thickness"] * 0.75 for r in reserved)
    ]

    for rib_index, center in enumerate(centers, start=1):
        create_planar_rib_safe(
            doc, group, placement, descriptor["index"],
            rib_index, center, p
        )

    hug_start = len(centers) + 1
    for offset, center in enumerate(hug_centers, start=0):
        create_planar_rib_safe(
            doc, group, placement, descriptor["index"],
            hug_start + offset, center, p
        )

    for center in connection_centers:
        create_connection_rib_safe(
            doc, group, placement, descriptor["index"], center, p
        )

    return {
        "ribs": len(centers) + len(hug_centers) + len(connection_centers),
        "frame_teeth": parts["tooth_count"],
    }


def create_leg_plate_feature(
    doc,
    parent,
    placement,
    name,
    label,
    x0,
    y0,
    z0,
    width,
    depth,
    thickness,
):
    shape = Part.makeBox(
        width,
        depth,
        thickness,
        App.Vector(x0, y0, z0),
    )
    return create_shape_feature(
        doc,
        parent,
        name,
        label,
        shape,
        placement,
    )


def cap_tab_boxes(descriptor, p, x0, y0, z0, width, depth, thickness):
    if not tampa_costela_enabled(p):
        return []
    mode = p["cap_rib_sides"]
    if mode == "Automático":
        side_count = 2 if descriptor["kind"] == "axis_corner" else 1
    elif mode == "2 lados internos":
        side_count = 2
    else:
        side_count = 1

    tab_depth = tooth_depth(p)
    tab_count = p["rib_tab_count"]
    tab_width = p["rib_tab_width"]
    boxes = []
    radius = p["tooth_hole_diameter"] / 2.0
    over = max(2.0, radius * 0.75)

    # Lado interno Y: dentes distribuídos no sentido X.
    for a, b in distributed_ranges(x0, width, tab_count, tab_width):
        tab = Part.makeBox(
            b - a, tab_depth, thickness, App.Vector(a, y0 + depth, z0)
        )
        if p.get("tooth_holes_cap", False):
            cutters = [
                Part.makeCylinder(
                    radius, thickness + 2.0 * over,
                    App.Vector(
                        x_center, y0 + depth + tab_depth / 2.0, z0 - over
                    ),
                    App.Vector(0, 0, 1),
                )
                for x_center in tooth_hole_centers(a, b, p)
            ]
            tab = safe_cut_shape(
                tab, cutters, "furos individuais da tampa-costela em Y"
            )
        boxes.append(tab)

    # Em perna de canto, o segundo lado interno é X.
    if side_count >= 2:
        for a, b in distributed_ranges(y0, depth, tab_count, tab_width):
            tab = Part.makeBox(
                tab_depth, b - a, thickness, App.Vector(x0 + width, a, z0)
            )
            if p.get("tooth_holes_cap", False):
                cutters = [
                    Part.makeCylinder(
                        radius, thickness + 2.0 * over,
                        App.Vector(
                            x0 + width + tab_depth / 2.0,
                            y_center, z0 - over,
                        ),
                        App.Vector(0, 0, 1),
                    )
                    for y_center in tooth_hole_centers(a, b, p)
                ]
                tab = safe_cut_shape(
                    tab, cutters, "furos individuais da tampa-costela em X"
                )
            boxes.append(tab)
    return boxes


def leg_connection_slot_tool(descriptor, p, z0, thickness):
    if not (
        descriptor.get("kind") == "axis_edge"
        and p.get("create_t_connection_rib", False)
        and p.get("deep_lower_tooth", False)
    ):
        return None

    leg_w, leg_d = leg_dimensions(p)
    clearance = p["rib_slot_clearance"]
    slot_x0 = leg_w / 2.0 - p["rib_thickness"] / 2.0 - clearance
    slot_x1 = leg_w / 2.0 + p["rib_thickness"] / 2.0 + clearance
    tooth_w = min(
        max(p["rib_tab_width"], p["rib_thickness"] * 2.0),
        leg_d * 0.70,
    )
    slot_y0 = leg_d / 2.0 - tooth_w / 2.0 - clearance
    slot_y1 = leg_d / 2.0 + tooth_w / 2.0 + clearance
    return integrated_slot_xy(
        slot_x0, slot_x1, slot_y0, slot_y1,
        z0 - 0.5, thickness + 1.0, p,
    )


def create_leg_caps_and_toco(
    doc,
    group,
    placement,
    descriptor,
    p,
    result_index,
    frame_bottom_z,
    tube_start_z,
):
    created_caps = 0
    created_toco_plates = 0
    created_cap_ribs = 0
    created_shoulders = 0
    leg_w, leg_d = leg_dimensions(p)
    cap_t = cap_thickness(p)
    total_length = descriptor["length"]

    # Ombro externo: fecha o vão visível e recebe diretamente o painel
    # inferior do quadro. A face superior coincide com a face inferior
    # do quadro; o corpo tubular começa abaixo dele.
    if support_shoulder_enabled(p):
        shoulder_w, shoulder_d, shoulder_x0, shoulder_y0 = shoulder_dimensions(p)
        shoulder_t = shoulder_thickness(p)
        shoulder_shape = Part.makeBox(
            shoulder_w,
            shoulder_d,
            shoulder_t,
            App.Vector(shoulder_x0, shoulder_y0, frame_bottom_z),
        )
        shoulder_slot = leg_connection_slot_tool(
            descriptor, p, frame_bottom_z, shoulder_t
        )
        if shoulder_slot is not None:
            shoulder_shape = safe_cut_shape(
                shoulder_shape, [shoulder_slot], "ombro de apoio"
            )
        create_shape_feature(
            doc, group,
            "Ombro_Apoio_Perna_{:02d}".format(result_index),
            "Ombro de apoio — perna {:02d}".format(result_index),
            shoulder_shape, placement,
        )
        created_shoulders += 1

    if upper_cap_enabled(p):
        # A tampa superior é encaixada simetricamente à inferior:
        # começa na extremidade superior do tubo e avança uma espessura para dentro.
        cap_w, cap_d, cap_x0, cap_y0 = internal_cap_dimensions(p)
        upper_z = tube_start_z + cap_recess(p)
        base = Part.makeBox(
            cap_w, cap_d, cap_t,
            App.Vector(cap_x0, cap_y0, upper_z),
        )
        cap_slot = leg_connection_slot_tool(
            descriptor, p, upper_z, cap_t
        )
        if cap_slot is not None:
            base = safe_cut_shape(
                base, [cap_slot], "tampa interna da conexão T"
            )

        if tampa_costela_enabled(p):
            shape_parts = [base] + cap_tab_boxes(
                descriptor, p,
                cap_x0, cap_y0, upper_z,
                cap_w, cap_d, cap_t,
            )
            shape_parts += leg_cap_tab_boxes(p, upper_z, leg_w, leg_d, cap_t)
            shape = safe_fuse_shapes(shape_parts, "tampa superior dentada da perna")
            label = "Tampa-costela interna dentada — perna {:02d}".format(result_index)
            created_cap_ribs += 1
        else:
            cap_parts = [base] + leg_cap_tab_boxes(p, upper_z, leg_w, leg_d, cap_t)
            shape = safe_fuse_shapes(cap_parts, "tampa superior da perna")
            label = (
                "Tampa superior interna dentada — perna {:02d}"
                if leg_cap_joint_enabled(p)
                else "Tampa superior interna — perna {:02d}"
            ).format(result_index)

        cap_root_reliefs = male_tab_root_reliefs_leg_cap(
            p, upper_z, leg_w, leg_d, cap_t
        )
        cap_root_reliefs += male_tab_root_reliefs_cap_rib(
            descriptor, p,
            cap_x0, cap_y0, upper_z,
            cap_w, cap_d, cap_t,
        )
        shape = safe_cut_shape(
            shape,
            cap_root_reliefs,
            "dogbone nas raízes da tampa superior e tampa-costela",
        )
        shape = safe_cut_shape(
            shape,
            cap_male_tooth_hole_cutters(
                p, upper_z, leg_w, leg_d, cap_t
            ),
            "furos reais nos dentes da tampa superior da perna",
        )
        create_shape_feature(
            doc, group,
            "Tampa_Superior_Perna_{:02d}".format(result_index),
            label, shape, placement,
        )
        created_caps += 1

        if toco_enabled(p):
            toco_w, toco_d = toco_dimensions(p)
            plate_t = toco_plate_thickness(p)
            x0 = (leg_w - toco_w) / 2.0
            y0 = (leg_d - toco_d) / 2.0

            # O toco nasce diretamente sobre a face superior da tampa.
            # Como o eixo local Z aponta para o piso, as chapas crescem no sentido -Z.
            for plate_index in range(1, p["toco_plate_count"] + 1):
                z0 = upper_z - plate_index * plate_t
                plate_shape = Part.makeBox(
                    toco_w, toco_d, plate_t,
                    App.Vector(x0, y0, z0),
                )
                plate_slot = leg_connection_slot_tool(
                    descriptor, p, z0, plate_t
                )
                if plate_slot is not None:
                    plate_shape = safe_cut_shape(
                        plate_shape, [plate_slot],
                        "chapa do toco da conexão T",
                    )
                create_shape_feature(
                    doc, group, placement=placement,
                    name="Chapa_Toco_{:02d}_{:02d}".format(
                        result_index, plate_index
                    ),
                    label="Chapa do toco {:02d}/{:02d}".format(
                        result_index, plate_index
                    ),
                    shape=plate_shape,
                )
                created_toco_plates += 1

    if lower_cap_enabled(p):
        cap_w, cap_d, cap_x0, cap_y0 = internal_cap_dimensions(p)
        lower_z = lower_cap_z(p, total_length, cap_t)
        base = Part.makeBox(cap_w, cap_d, cap_t, App.Vector(cap_x0, cap_y0, lower_z))
        cap_parts = [base] + leg_cap_tab_boxes(p, lower_z, leg_w, leg_d, cap_t)
        lower_shape = safe_fuse_shapes(cap_parts, "tampa inferior da perna")
        lower_shape = safe_cut_shape(
            lower_shape,
            male_tab_root_reliefs_leg_cap(
                p, lower_z, leg_w, leg_d, cap_t
            ),
            "dogbone nas raízes da tampa inferior",
        )
        lower_shape = safe_cut_shape(
            lower_shape,
            cap_male_tooth_hole_cutters(
                p, lower_z, leg_w, leg_d, cap_t
            ),
            "furos reais nos dentes da tampa inferior da perna",
        )
        lower_shape = safe_cut_shape(
            lower_shape,
            leveler_cutters(p, lower_z, leg_w, leg_d, cap_t),
            "furo e rebaixo do nivelador",
        )
        create_shape_feature(
            doc, group,
            "Tampa_Inferior_Perna_{:02d}".format(result_index),
            (
                "Tampa inferior no piso dentada — {:02d}"
                if leg_cap_joint_enabled(p)
                else "Tampa inferior no piso — {:02d}"
            ).format(result_index),
            lower_shape,
            placement,
        )
        created_caps += 1

    return (
        created_caps,
        created_toco_plates,
        created_cap_ribs,
        created_shoulders,
    )


def create_axis_segment(doc, root, descriptor, p, result_index):
    suffix = "{:02d}".format(result_index)
    centered = descriptor["kind"] == "axis_center"
    is_attached_leg = descriptor["kind"] in ("axis_corner", "axis_edge")

    if descriptor["kind"] == "axis_corner":
        label_kind = "Perna de canto"
    elif descriptor["kind"] == "axis_edge":
        label_kind = "Perna intermediária"
    else:
        label_kind = "Barra 3D por eixo"

    group = doc.addObject("App::Part", "Segmento_Seguro_3D_" + suffix)
    group.Label = "{} {} — {:.2f} mm".format(label_kind, suffix, descriptor["length"])
    mark_generated(group)
    root.addObject(group)

    origin = descriptor["origin"].add(App.Vector(0.0, 0.0, p["legacy_z"]))
    placement = matrix_placement(
        origin,
        descriptor["axis_x"],
        descriptor["axis_y"],
        descriptor["axis_z"],
    )

    frame_bottom_z = 0.0
    tube_start_z = 0.0
    tube_length = descriptor["length"]
    width = p["profile_width"]
    depth = p["profile_height"]

    if is_attached_leg:
        width, depth = leg_dimensions(p)
        if leg_no_joint(p):
            frame_bottom_z = p["profile_height"]
            shoulder_t = (
                shoulder_thickness(p)
                if support_shoulder_enabled(p)
                else 0.0
            )
            tube_start_z = max(
                0.0,
                frame_bottom_z - leg_frame_penetration(p) + shoulder_t,
            )
            tube_length = descriptor["length"] - tube_start_z
            minimum = cap_thickness(p) if upper_cap_enabled(p) else TOL
            if tube_length <= max(TOL, minimum):
                raise ValueError(
                    "A linha da perna é curta demais para descontar "
                    "a altura do quadro e o ombro de apoio."
                )

    rib_length = tube_length if is_attached_leg else descriptor["length"]
    centers = calculate_rib_centers(rib_length, p)
    centers_local = [
        c + (tube_start_z if is_attached_leg else 0.0)
        for c in centers
    ]

    leg_parts = make_axis_tube_parts(
        descriptor, p,
        z_start=tube_start_z,
        tube_length=tube_length,
        width=width,
        depth=depth,
        rib_centers=centers_local,
    )

    # V4.5: cada chapa da perna é uma peça física independente.
    # Isso deixa os dentes e os rasgos visíveis na árvore e evita
    # converter um composto complexo em sólido.
    dentada = leg_joint_enabled(p)
    create_shape_feature(
        doc, group,
        "Painel_Frontal_Perna_" + suffix,
        ("Painel frontal dentado — " if dentada else "Painel frontal liso — ") + suffix,
        leg_parts["front"],
        placement,
    )
    create_shape_feature(
        doc, group,
        "Painel_Traseiro_Perna_" + suffix,
        ("Painel traseiro dentado — " if dentada else "Painel traseiro liso — ") + suffix,
        leg_parts["back"],
        placement,
    )
    create_shape_feature(
        doc, group,
        "Painel_Esquerdo_Perna_" + suffix,
        ("Painel esquerdo com rasgos — " if dentada else "Painel esquerdo liso — ") + suffix,
        leg_parts["left"],
        placement,
    )
    create_shape_feature(
        doc, group,
        "Painel_Direito_Perna_" + suffix,
        ("Painel direito com rasgos — " if dentada else "Painel direito liso — ") + suffix,
        leg_parts["right"],
        placement,
    )

    created_caps = 0
    created_toco_plates = 0
    created_cap_ribs = 0
    created_shoulders = 0

    if is_attached_leg and leg_no_joint(p):
        (
            created_caps,
            created_toco_plates,
            created_cap_ribs,
            created_shoulders,
        ) = create_leg_caps_and_toco(
            doc, group, placement, descriptor, p, result_index,
            frame_bottom_z, tube_start_z,
        )

    for rib_index, center_local in enumerate(centers_local, start=1):
        create_axis_rib_safe(
            doc, group, placement,
            result_index, rib_index,
            center_local, p, centered,
        )

    return {
        "ribs": len(centers),
        "caps": created_caps,
        "toco_plates": created_toco_plates,
        "cap_ribs": created_cap_ribs,
        "shoulders": created_shoulders,
        "leg_teeth": leg_parts["tooth_count"],
    }


# =============================================================================
# Interpretação automática
# =============================================================================

def edge_records_from_ids(edge_ids, graph_edges):
    return [
        {
            "p0": App.Vector(graph_edges[edge_id]["p0"]),
            "p1": App.Vector(graph_edges[edge_id]["p1"]),
            "source": graph_edges[edge_id]["source"],
            "graph_id": edge_id,
        }
        for edge_id in edge_ids
    ]


def find_simple_planar_cycle(nodes, graph_edges, adjacency):
    core_edges = find_two_core(graph_edges, adjacency)
    if not core_edges:
        return None

    components = connected_edge_components(
        core_edges,
        graph_edges,
        adjacency,
    )

    # Uma mesa espacial pode ter mais de um quadro fechado no mesmo objeto:
    # tampo, travessas inferiores e/ou bases.  A versão anterior tratava isso
    # como erro e nem começava a gerar o móvel.  Cada componente retornado por
    # ``cycle_components`` já é um ciclo simples; portanto escolhemos de modo
    # determinístico o de maior área como contorno principal.  Os demais
    # continuam na lista de arestas da rede para serem lidos como estrutura 3D
    # — não são apagados nem fundidos ao contorno escolhido.
    candidates = []
    for component in components:
        try:
            vertices, ordered_edges = order_cycle(
                component,
                nodes,
                graph_edges,
                adjacency,
            )
            candidates.append((polygon_area_3d(vertices), len(component), vertices, ordered_edges))
        except ValueError:
            # Componentes ramificados não podem ser o limite externo, mas ainda
            # permanecem disponíveis como rede 3D no chamador.
            continue

    if not candidates:
        raise ValueError(
            "Nenhum ciclo fechado simples pôde ser usado como contorno externo."
        )

    candidates.sort(key=lambda item: (item[0], item[1]), reverse=True)
    _, _, vertices, ordered_edges = candidates[0]

    return {
        "vertices": vertices,
        "edge_ids": ordered_edges,
    }


def polygon_area_3d(vertices):
    """Área aproximada do ciclo projetada no próprio plano."""
    if len(vertices) < 3:
        return 0.0
    try:
        normal = first_valid_normal(vertices)
        origin = vertices[0]
        axis_u = vector_unit(vertices[1].sub(origin))
        axis_v = vector_unit(normal.cross(axis_u))
        projected = []
        for point in vertices:
            delta = point.sub(origin)
            projected.append((delta.dot(axis_u), delta.dot(axis_v)))
        return abs(signed_area(projected))
    except Exception:
        return 0.0


def find_best_contour_source(sources):
    """
    Procura, objeto por objeto, o maior ciclo fechado simples.

    Isso impede que a ordem de seleção altere acidentalmente o SketchOrigem.
    """
    candidates = []
    for source in sources:
        try:
            source_edges = extract_all_edges([source])
            nodes, graph_edges, adjacency = build_graph(source_edges)
            cycle = find_simple_planar_cycle(nodes, graph_edges, adjacency)
            if cycle is None:
                continue
            area = polygon_area_3d(cycle["vertices"])
            perimeter = sum(
                vector_distance(
                    cycle["vertices"][idx],
                    cycle["vertices"][(idx + 1) % len(cycle["vertices"])],
                )
                for idx in range(len(cycle["vertices"]))
            )
            candidates.append((area, perimeter, source, source_edges))
        except Exception:
            continue

    if not candidates:
        return None, None

    candidates.sort(key=lambda item: (item[0], item[1]), reverse=True)
    _area, _perimeter, source, source_edges = candidates[0]
    return source, source_edges



def secondary_planar_cycles(sources, primary_source, all_edges, primary_plane, p):
    """Detecta sketches fechados secundários e os converte em quadros completos."""
    frames = []
    used_keys = set()

    for source in sources:
        if source is primary_source:
            continue
        try:
            source_edges = extract_all_edges([source])
            nodes, graph_edges, adjacency = build_graph(source_edges)
            cycle = find_simple_planar_cycle(nodes, graph_edges, adjacency)
            if cycle is None:
                continue

            cycle_keys = {
                edge_key(source_edges[idx])
                for idx in cycle["edge_ids"]
            }
            other_edges = [
                edge for edge in all_edges
                if edge_key(edge) not in cycle_keys
            ]
            plane = plane_basis(
                cycle["vertices"], other_edges, p["height_direction"]
            )

            # Um ciclo coplanar ao quadro principal não é promovido a segundo
            # quadro: isso duplicava toda a estrutura e gerava tocos nos cantos.
            if primary_plane is not None:
                parallel = abs(plane["normal"].dot(primary_plane["normal"]))
                if parallel < 0.95:
                    continue
                plane_offset = abs(
                    plane["origin"].sub(primary_plane["origin"]).dot(
                        primary_plane["normal"]
                    )
                )
                if plane_offset <= max(PLANAR_TOL * 10.0, p["wall"] * 0.20):
                    used_keys.update(cycle_keys)
                    continue
                if plane["normal"].dot(primary_plane["normal"]) < 0:
                    plane["normal"] = plane["normal"].multiply(-1.0)
                    plane["axis_v"] = plane["axis_v"].multiply(-1.0)

            segments = calculate_planar_segments(
                plane, p["profile_width"], p["connection"]
            )
            frames.append({
                "source": source,
                "plane": plane,
                "segments": segments,
                "edge_keys": cycle_keys,
            })
            used_keys.update(cycle_keys)
        except Exception as exc:
            App.Console.PrintWarning(
                "Sketch secundário não convertido em quadro: {}.\n".format(exc)
            )

    return frames, used_keys



def loop_side_attachment(point, plane, tolerance):
    best = None
    vertices = plane["vertices"]
    for index in range(len(vertices)):
        start = vertices[index]
        end = vertices[(index + 1) % len(vertices)]
        t, projected, distance = project_point_to_segment(point, start, end)
        candidate = (distance, index, t, projected)
        if best is None or candidate[0] < best[0]:
            best = candidate
    if best is None or best[0] > tolerance:
        return None
    return {
        "distance": best[0],
        "side_index": best[1],
        "side_t": best[2],
        "point": App.Vector(best[3]),
    }


def perpendicular_leg_at_point(edges, point, plane, tolerance):
    """Há uma linha saindo do plano no ponto informado?"""
    for edge in edges:
        for attached, other in ((edge["p0"], edge["p1"]), (edge["p1"], edge["p0"])):
            if vector_distance(attached, point) > tolerance:
                continue
            direction = other.sub(attached)
            if direction.Length <= TOL:
                continue
            if abs(vector_unit(direction).dot(plane["normal"])) >= 0.90:
                return True
    return False


def trim_to_inner_face(direction, side_index, plane, profile_width, entering=True):
    vertices = plane["vertices"]
    start = vertices[side_index]
    end = vertices[(side_index + 1) % len(vertices)]
    side = end.sub(start)
    if side.Length <= TOL:
        return 0.0
    side_axis = vector_unit(side)
    inward = vector_unit(plane["normal"].cross(side_axis))
    # ``Vector.multiply`` altera o próprio vetor no FreeCAD.  Esta rotina é
    # chamada duas vezes para uma travessa (entrada e saída); inverter
    # ``direction`` in-place na segunda chamada invertia o eixo que o
    # chamador ainda usaria para posicionar início/fim.  O efeito visível era
    # a travessa crescer para fora do quadro nos dois lados.  Trabalhamos
    # sempre numa cópia local do sentido de viagem.
    travel = App.Vector(direction)
    if not entering:
        travel = vector_scaled(travel, -1.0)
    cosine = travel.dot(inward)
    if cosine < 0:
        inward = inward.multiply(-1.0)
        cosine = travel.dot(inward)
    cosine = abs(cosine)
    if cosine <= 0.10:
        return 0.0
    return profile_width / cosine



def _plane_uv(point, plane):
    delta = App.Vector(point).sub(plane["origin"])
    return (delta.dot(plane["axis_u"]), delta.dot(plane["axis_v"]))


def _plane_point(uv, plane):
    return (
        App.Vector(plane["origin"])
        .add(plane["axis_u"].multiply(uv[0]))
        .add(plane["axis_v"].multiply(uv[1]))
    )


def _cross2(a, b):
    return a[0] * b[1] - a[1] * b[0]


def _canonical_direction_2d(vector):
    length = math.hypot(vector[0], vector[1])
    if length <= TOL:
        return None
    direction = (vector[0] / length, vector[1] / length)
    if direction[0] < -ANGLE_TOL or (
        abs(direction[0]) <= ANGLE_TOL and direction[1] < 0.0
    ):
        direction = (-direction[0], -direction[1])
    return direction


def _point_segment_distance_2d(point, start, end):
    dx = end[0] - start[0]
    dy = end[1] - start[1]
    span2 = dx * dx + dy * dy
    if span2 <= TOL * TOL:
        return math.hypot(point[0] - start[0], point[1] - start[1])
    t = ((point[0] - start[0]) * dx + (point[1] - start[1]) * dy) / span2
    t = max(0.0, min(1.0, t))
    projected = (start[0] + t * dx, start[1] + t * dy)
    return math.hypot(point[0] - projected[0], point[1] - projected[1])


def _distance_to_polygon_2d(point, polygon):
    best = None
    for index in range(len(polygon)):
        start = polygon[index]
        end = polygon[(index + 1) % len(polygon)]
        distance = _point_segment_distance_2d(point, start, end)
        if best is None or distance < best:
            best = distance
    return best if best is not None else 1e100


def _clip_segment_to_convex_polygon(start, end, polygon, tolerance):
    """Recorta um segmento contra um polígono convexo orientado anti-horário."""
    direction = (end[0] - start[0], end[1] - start[1])
    t_min = 0.0
    t_max = 1.0

    for index in range(len(polygon)):
        a = polygon[index]
        b = polygon[(index + 1) % len(polygon)]
        edge = (b[0] - a[0], b[1] - a[1])
        base = _cross2(edge, (start[0] - a[0], start[1] - a[1]))
        slope = _cross2(edge, direction)

        # Interior = lado esquerdo da aresta.
        if abs(slope) <= TOL:
            if base < -tolerance:
                return None
            continue

        boundary = (-tolerance - base) / slope
        if slope > 0.0:
            t_min = max(t_min, boundary)
        else:
            t_max = min(t_max, boundary)
        if t_min > t_max + TOL:
            return None

    clipped_start = (
        start[0] + direction[0] * t_min,
        start[1] + direction[1] * t_min,
    )
    clipped_end = (
        start[0] + direction[0] * t_max,
        start[1] + direction[1] * t_max,
    )
    if math.hypot(
        clipped_end[0] - clipped_start[0],
        clipped_end[1] - clipped_start[1],
    ) <= TOL:
        return None
    return clipped_start, clipped_end


def _merge_scalar_intervals(intervals, tolerance):
    intervals = sorted((min(a, b), max(a, b)) for a, b in intervals)
    merged = []
    for start, end in intervals:
        if end - start <= TOL:
            continue
        if not merged or start > merged[-1][1] + tolerance:
            merged.append([start, end])
        else:
            merged[-1][1] = max(merged[-1][1], end)
    return [(item[0], item[1]) for item in merged]


def _vertical_leg_positions_on_member(edges, center_start, center_end, plane, tolerance):
    positions = []
    member_vector = center_end.sub(center_start)
    member_length = member_vector.Length
    if member_length <= TOL:
        return positions
    member_axis = vector_unit(member_vector)

    for edge in edges:
        p0 = App.Vector(edge["p0"])
        p1 = App.Vector(edge["p1"])
        distances = (
            abs(p0.sub(plane["origin"]).dot(plane["normal"])),
            abs(p1.sub(plane["origin"]).dot(plane["normal"])),
        )
        if min(distances) > tolerance:
            continue
        attached = p0 if distances[0] <= distances[1] else p1
        other = p1 if attached is p0 else p0
        vector = other.sub(attached)
        if vector.Length <= TOL:
            continue
        if abs(vector_unit(vector).dot(plane["normal"])) < 0.90:
            continue
        parameter, projected, distance = project_point_to_segment(
            attached, center_start, center_end
        )
        if distance <= tolerance and -TOL <= parameter <= 1.0 + TOL:
            positions.append(max(0.0, min(member_length, parameter * member_length)))

    return unique_scalar_centers(positions)


def detect_planar_network_members(network_edges, plane, p):
    """
    Interpreta uma rede planar de maneira genérica.

    - cada linha coplanar é recortada pelo contorno externo;
    - trechos colineares partidos por cruzamentos são reunidos;
    - linhas horizontais, verticais ou inclinadas viram travessas reais;
    - redes quadriculadas geram uma estrutura por linha da malha;
    - linhas fora do plano permanecem disponíveis para pernas/barras 3D.
    """
    if plane is None:
        return [], list(network_edges)

    polygon = list(plane["projected"])
    tolerance = max(p["attach_tolerance"], PLANAR_TOL * 50.0, 0.20)
    angle_tolerance = 2.0e-3
    groups = []
    accepted_keys = set()

    for edge in network_edges:
        p0 = App.Vector(edge["p0"])
        p1 = App.Vector(edge["p1"])
        distance0 = abs(p0.sub(plane["origin"]).dot(plane["normal"]))
        distance1 = abs(p1.sub(plane["origin"]).dot(plane["normal"]))
        if distance0 > tolerance or distance1 > tolerance:
            continue

        uv0 = _plane_uv(p0, plane)
        uv1 = _plane_uv(p1, plane)
        direction = _canonical_direction_2d((uv1[0] - uv0[0], uv1[1] - uv0[1]))
        if direction is None:
            continue

        clipped = _clip_segment_to_convex_polygon(uv0, uv1, polygon, tolerance)
        if clipped is None:
            continue
        clipped0, clipped1 = clipped
        midpoint = (
            (clipped0[0] + clipped1[0]) / 2.0,
            (clipped0[1] + clipped1[1]) / 2.0,
        )

        # Linhas coincidentes com o perímetro não são travessas internas.
        if _distance_to_polygon_2d(midpoint, polygon) <= tolerance * 0.75:
            continue

        normal = (-direction[1], direction[0])
        offset = normal[0] * clipped0[0] + normal[1] * clipped0[1]
        start_t = direction[0] * clipped0[0] + direction[1] * clipped0[1]
        end_t = direction[0] * clipped1[0] + direction[1] * clipped1[1]

        group = None
        for candidate in groups:
            if abs(_cross2(direction, candidate["direction"])) > angle_tolerance:
                continue
            if abs(offset - candidate["offset"]) > tolerance:
                continue
            group = candidate
            break
        if group is None:
            group = {
                "direction": direction,
                "normal": normal,
                "offset": offset,
                "intervals": [],
                "sources": [],
            }
            groups.append(group)
        group["intervals"].append((start_t, end_t))
        group["sources"].append(edge.get("source"))
        accepted_keys.add(edge_key(edge))

    members = []
    member_keys = set()

    for group in groups:
        intervals = _merge_scalar_intervals(group["intervals"], tolerance)
        direction = group["direction"]
        normal2d = group["normal"]
        offset = group["offset"]

        for start_t, end_t in intervals:
            uv_start = (
                direction[0] * start_t + normal2d[0] * offset,
                direction[1] * start_t + normal2d[1] * offset,
            )
            uv_end = (
                direction[0] * end_t + normal2d[0] * offset,
                direction[1] * end_t + normal2d[1] * offset,
            )
            center_start = _plane_point(uv_start, plane)
            center_end = _plane_point(uv_end, plane)
            raw = center_end.sub(center_start)
            if raw.Length <= max(TOL, p["wall"]):
                continue

            attach_start = loop_side_attachment(center_start, plane, tolerance * 2.0)
            attach_end = loop_side_attachment(center_end, plane, tolerance * 2.0)
            axis_x = vector_unit(raw)
            trim_start = 0.0
            trim_end = 0.0
            if attach_start is not None:
                trim_start = trim_to_inner_face(
                    axis_x, attach_start["side_index"], plane,
                    p["profile_width"], True,
                )
            if attach_end is not None:
                trim_end = trim_to_inner_face(
                    axis_x, attach_end["side_index"], plane,
                    p["profile_width"], False,
                )
            trim_start = min(max(0.0, trim_start), raw.Length * 0.40)
            trim_end = min(max(0.0, trim_end), raw.Length * 0.40)
            member_length = raw.Length - trim_start - trim_end
            if member_length <= p["profile_width"] * 0.60:
                continue

            center_start = center_start.add(axis_x.multiply(trim_start))
            center_end = center_start.add(axis_x.multiply(member_length))
            axis_z = App.Vector(plane["normal"])
            axis_y_vector = axis_z.cross(axis_x)
            if axis_y_vector.Length <= TOL:
                continue
            axis_y = vector_unit(axis_y_vector)
            origin = center_start.sub(axis_y.multiply(p["profile_width"] / 2.0))

            key = (
                quantized_point(center_start, 1e3),
                quantized_point(center_end, 1e3),
            )
            key = tuple(sorted(key))
            if key in member_keys:
                continue
            member_keys.add(key)

            leg_positions = _vertical_leg_positions_on_member(
                network_edges, center_start, center_end, plane, tolerance * 2.0
            )
            descriptor = {
                "kind": "planar_network",
                "index": 0,
                "start": origin,
                "end": App.Vector(
                origin.x + axis_x.x * member_length,
                origin.y + axis_x.y * member_length,
                origin.z + axis_x.z * member_length,
            ),
                "length": member_length,
                "axis_x": axis_x,
                "axis_y": axis_y,
                "axis_z": axis_z,
                "footprint": [
                    (0.0, 0.0),
                    (member_length, 0.0),
                    (member_length, p["profile_width"]),
                    (0.0, p["profile_width"]),
                ],
                "internal_member": True,
                "network_member": True,
                "start_leg": bool(leg_positions and leg_positions[0] <= tolerance * 2.0),
                "end_leg": bool(leg_positions and leg_positions[-1] >= member_length - tolerance * 2.0),
                "leg_positions": leg_positions,
                "source": group["sources"][0] if group["sources"] else None,
            }
            members.append(descriptor)

    remaining = [
        edge for edge in network_edges
        if edge_key(edge) not in accepted_keys
    ]
    return members, remaining


def detect_direct_planar_members(network_edges, plane, p, existing_members=None):
    """
    Fallback simples e deliberadamente permissivo.

    Cada segmento reto coplanar que não coincide com o perímetro e cujo ponto
    médio está dentro do contorno vira uma travessa. É usado quando a leitura
    por agrupamento não encontrou a linha ou deixou segmentos remanescentes.
    """
    if plane is None:
        return [], list(network_edges)

    existing_members = list(existing_members or [])
    existing_keys = set()
    for descriptor in existing_members:
        a = quantized_point(descriptor["start"], 1e3)
        b = quantized_point(descriptor["end"], 1e3)
        existing_keys.add(tuple(sorted((a, b))))

    polygon = list(plane["projected"])
    tolerance = max(p["attach_tolerance"], 0.30)
    members = []
    remaining = []

    for edge in network_edges:
        p0 = App.Vector(edge["p0"])
        p1 = App.Vector(edge["p1"])
        raw = p1.sub(p0)
        if raw.Length <= max(TOL, p["wall"] * 0.25):
            continue

        d0 = abs(p0.sub(plane["origin"]).dot(plane["normal"]))
        d1 = abs(p1.sub(plane["origin"]).dot(plane["normal"]))
        if d0 > tolerance or d1 > tolerance:
            remaining.append(edge)
            continue

        uv0 = _plane_uv(p0, plane)
        uv1 = _plane_uv(p1, plane)
        clipped = _clip_segment_to_convex_polygon(uv0, uv1, polygon, tolerance)
        if clipped is None:
            remaining.append(edge)
            continue

        uv_a, uv_b = clipped
        midpoint_uv = ((uv_a[0] + uv_b[0]) / 2.0, (uv_a[1] + uv_b[1]) / 2.0)
        # Só rejeita uma aresta quando o segmento inteiro está sobre o mesmo lado do perímetro.
        d_mid = _distance_to_polygon_2d(midpoint_uv, polygon)
        d_a = _distance_to_polygon_2d(uv_a, polygon)
        d_b = _distance_to_polygon_2d(uv_b, polygon)
        if d_mid <= tolerance and d_a <= tolerance and d_b <= tolerance:
            remaining.append(edge)
            continue

        center_start = _plane_point(uv_a, plane)
        center_end = _plane_point(uv_b, plane)
        raw = center_end.sub(center_start)
        if raw.Length <= p["profile_width"] * 0.60:
            continue
        axis_x = vector_unit(raw)

        attach_start = loop_side_attachment(center_start, plane, tolerance * 3.0)
        attach_end = loop_side_attachment(center_end, plane, tolerance * 3.0)
        trim_start = 0.0
        trim_end = 0.0
        if attach_start is not None:
            trim_start = max(0.0, trim_to_inner_face(
                axis_x, attach_start["side_index"], plane,
                p["profile_width"], True,
            ))
        if attach_end is not None:
            trim_end = max(0.0, trim_to_inner_face(
                axis_x, attach_end["side_index"], plane,
                p["profile_width"], False,
            ))
        trim_start = min(trim_start, raw.Length * 0.40)
        trim_end = min(trim_end, raw.Length * 0.40)
        member_length = raw.Length - trim_start - trim_end
        if member_length <= p["profile_width"] * 0.60:
            continue

        center_start = center_start.add(axis_x.multiply(trim_start))
        center_end = center_start.add(axis_x.multiply(member_length))
        axis_z = App.Vector(plane["normal"])
        axis_y_raw = axis_z.cross(axis_x)
        if axis_y_raw.Length <= TOL:
            continue
        axis_y = vector_unit(axis_y_raw)
        origin = center_start.sub(axis_y.multiply(p["profile_width"] / 2.0))

        key = tuple(sorted((
            quantized_point(center_start, 1e3),
            quantized_point(center_end, 1e3),
        )))
        if key in existing_keys:
            continue
        existing_keys.add(key)

        leg_positions = _vertical_leg_positions_on_member(
            network_edges, center_start, center_end, plane, tolerance * 3.0
        )
        members.append({
            "kind": "planar_direct_fallback",
            "index": 0,
            "start": origin,
            "end": origin.add(axis_x.multiply(member_length)),
            "length": member_length,
            "axis_x": axis_x,
            "axis_y": axis_y,
            "axis_z": axis_z,
            "footprint": [
                (0.0, 0.0),
                (member_length, 0.0),
                (member_length, p["profile_width"]),
                (0.0, p["profile_width"]),
            ],
            "internal_member": True,
            "network_member": True,
            "direct_fallback": True,
            "start_leg": bool(leg_positions and leg_positions[0] <= tolerance * 2.0),
            "end_leg": bool(leg_positions and leg_positions[-1] >= member_length - tolerance * 2.0),
            "leg_positions": leg_positions,
            "source": edge.get("source"),
        })

    return members, remaining



def _descriptor_centerline_key(descriptor, p, scale=1e3):
    """Chave geométrica independente do deslocamento lateral da travessa."""
    center_start = App.Vector(descriptor["start"]).add(
        vector_scaled(descriptor["axis_y"], p["profile_width"] / 2.0)
    )
    center_end = App.Vector(center_start).add(
        vector_scaled(descriptor["axis_x"], descriptor["length"])
    )
    return tuple(sorted((
        quantized_point(center_start, scale),
        quantized_point(center_end, scale),
    )))


def detect_boundary_to_boundary_members(all_edges, plane, p, existing_members=None):
    """
    Terceira rota de leitura, deliberadamente simples e determinística.

    Examina todas as linhas originais, inclusive as que desapareceram da lista
    remanescente do grafo. Se uma linha coplanar possui o ponto médio dentro do
    contorno e liga dois lados diferentes, ela vira uma travessa obrigatória.
    """
    if plane is None:
        return []

    existing_members = list(existing_members or [])
    existing_keys = {
        _descriptor_centerline_key(item, p)
        for item in existing_members
    }
    tolerance = max(p["attach_tolerance"], PLANAR_TOL * 50.0, 0.50)
    members = []

    for edge in all_edges:
        p0 = App.Vector(edge["p0"])
        p1 = App.Vector(edge["p1"])
        raw_original = p1.sub(p0)
        if raw_original.Length <= max(TOL, p["wall"] * 0.25):
            continue

        if (
            abs(p0.sub(plane["origin"]).dot(plane["normal"])) > tolerance
            or abs(p1.sub(plane["origin"]).dot(plane["normal"])) > tolerance
        ):
            continue

        midpoint = p0.add(raw_original.multiply(0.5))
        midpoint_uv = _plane_uv(midpoint, plane)
        # Arestas do perímetro possuem o ponto médio sobre o contorno.
        if _distance_to_polygon_2d(midpoint_uv, plane["projected"]) <= tolerance:
            continue
        if not point_inside_projected_polygon(midpoint, plane):
            continue

        attach0 = loop_side_attachment(p0, plane, tolerance * 2.0)
        attach1 = loop_side_attachment(p1, plane, tolerance * 2.0)
        if attach0 is None or attach1 is None:
            continue
        if attach0["side_index"] == attach1["side_index"]:
            continue

        start_contact = App.Vector(attach0["point"])
        end_contact = App.Vector(attach1["point"])
        raw = end_contact.sub(start_contact)
        if raw.Length <= p["profile_width"] * 1.10:
            continue
        axis_x = vector_unit(raw)

        trim_start = max(0.0, trim_to_inner_face(
            axis_x, attach0["side_index"], plane,
            p["profile_width"], True,
        ))
        trim_end = max(0.0, trim_to_inner_face(
            axis_x, attach1["side_index"], plane,
            p["profile_width"], False,
        ))
        trim_start = min(trim_start, raw.Length * 0.40)
        trim_end = min(trim_end, raw.Length * 0.40)
        member_length = raw.Length - trim_start - trim_end
        if member_length <= p["profile_width"] * 0.60:
            continue

        center_start = start_contact.add(axis_x.multiply(trim_start))
        axis_z = App.Vector(plane["normal"])
        axis_y_raw = axis_z.cross(axis_x)
        if axis_y_raw.Length <= TOL:
            continue
        axis_y = vector_unit(axis_y_raw)
        origin = center_start.sub(axis_y.multiply(p["profile_width"] / 2.0))

        descriptor = {
            "kind": "planar_forced_internal",
            "index": 0,
            "start": origin,
            "end": origin.add(axis_x.multiply(member_length)),
            "length": member_length,
            "axis_x": axis_x,
            "axis_y": axis_y,
            "axis_z": axis_z,
            "footprint": [
                (0.0, 0.0),
                (member_length, 0.0),
                (member_length, p["profile_width"]),
                (0.0, p["profile_width"]),
            ],
            "internal_member": True,
            "network_member": True,
            "forced_internal": True,
            "start_leg": perpendicular_leg_at_point(
                all_edges, start_contact, plane, tolerance * 2.0
            ),
            "end_leg": perpendicular_leg_at_point(
                all_edges, end_contact, plane, tolerance * 2.0
            ),
            "leg_positions": _vertical_leg_positions_on_member(
                all_edges,
                center_start,
                center_start.add(axis_x.multiply(member_length)),
                plane,
                tolerance * 2.0,
            ),
            "source": edge.get("source"),
        }
        key = _descriptor_centerline_key(descriptor, p)
        if key in existing_keys:
            continue
        existing_keys.add(key)
        members.append(descriptor)

    return members


def detect_internal_planar_members(network_edges, plane, p):
    """
    Converte linhas abertas e coplanares, ligadas de uma lateral à outra do
    contorno, em travessas tubulares. Essas linhas não devem virar Barra 3D.
    """
    if plane is None:
        return [], list(network_edges)

    members = []
    remaining = []
    tolerance = max(p["attach_tolerance"], PLANAR_TOL * 20.0)

    for edge in network_edges:
        p0 = App.Vector(edge["p0"])
        p1 = App.Vector(edge["p1"])
        d0 = abs(p0.sub(plane["origin"]).dot(plane["normal"]))
        d1 = abs(p1.sub(plane["origin"]).dot(plane["normal"]))
        line = p1.sub(p0)
        length = line.Length

        if length <= TOL or d0 > tolerance or d1 > tolerance:
            remaining.append(edge)
            continue

        direction = vector_unit(line)
        if abs(direction.dot(plane["normal"])) > 0.08:
            remaining.append(edge)
            continue

        attach0 = loop_side_attachment(p0, plane, tolerance)
        attach1 = loop_side_attachment(p1, plane, tolerance)
        if attach0 is None or attach1 is None:
            remaining.append(edge)
            continue
        if attach0["side_index"] == attach1["side_index"]:
            remaining.append(edge)
            continue

        midpoint = p0.add(line.multiply(0.5))
        if not point_inside_projected_polygon(midpoint, plane):
            remaining.append(edge)
            continue

        start_contact = attach0["point"]
        end_contact = attach1["point"]
        raw = end_contact.sub(start_contact)
        if raw.Length <= p["profile_width"] * 1.25:
            remaining.append(edge)
            continue
        axis_x = vector_unit(raw)

        trim_start = trim_to_inner_face(
            axis_x, attach0["side_index"], plane, p["profile_width"], True
        )
        trim_end = trim_to_inner_face(
            axis_x, attach1["side_index"], plane, p["profile_width"], False
        )
        trim_start = min(max(0.0, trim_start), raw.Length * 0.35)
        trim_end = min(max(0.0, trim_end), raw.Length * 0.35)
        member_length = raw.Length - trim_start - trim_end
        if member_length <= p["profile_width"]:
            remaining.append(edge)
            continue

        axis_z = App.Vector(plane["normal"])
        axis_y = vector_unit(axis_z.cross(axis_x))
        center_start = start_contact.add(axis_x.multiply(trim_start))
        origin = center_start.sub(axis_y.multiply(p["profile_width"] / 2.0))

        has_start_leg = perpendicular_leg_at_point(
            network_edges, start_contact, plane, tolerance
        )
        has_end_leg = perpendicular_leg_at_point(
            network_edges, end_contact, plane, tolerance
        )

        descriptor = {
            "kind": "planar_internal",
            "index": 0,
            "start": origin,
            "end": origin.add(axis_x.multiply(member_length)),
            "length": member_length,
            "axis_x": axis_x,
            "axis_y": axis_y,
            "axis_z": axis_z,
            "footprint": [
                (0.0, 0.0),
                (member_length, 0.0),
                (member_length, p["profile_width"]),
                (0.0, p["profile_width"]),
            ],
            "internal_member": True,
            "start_leg": has_start_leg,
            "end_leg": has_end_leg,
            "source": edge.get("source"),
        }
        members.append(descriptor)

    return members, remaining



def _edge_is_on_outer_perimeter(edge, plane, tolerance):
    """True only when both endpoints lie on the same outer perimeter side."""
    uv0 = _plane_uv(edge["p0"], plane)
    uv1 = _plane_uv(edge["p1"], plane)
    polygon = plane["projected"]
    for index in range(len(polygon)):
        a = polygon[index]
        b = polygon[(index + 1) % len(polygon)]
        if (
            _point_segment_distance_2d(uv0, a, b) <= tolerance
            and _point_segment_distance_2d(uv1, a, b) <= tolerance
        ):
            return True
    return False


def detect_raw_sketch_planar_members(all_edges, plane, p):
    """
    Deterministic planar-network reader.

    It does not depend on graph leftovers. Every original coplanar line that is
    not part of one outer perimeter side is promoted to a structural member.
    Collinear pieces split at grid intersections are merged again.
    """
    if plane is None:
        return [], set()

    tolerance = max(p["attach_tolerance"], PLANAR_TOL * 50.0, 0.50)
    angle_tolerance = 2.0e-3
    polygon = list(plane["projected"])
    groups = []
    used_keys = set()

    for edge in all_edges:
        p0 = App.Vector(edge["p0"])
        p1 = App.Vector(edge["p1"])
        raw3d = p1.sub(p0)
        if raw3d.Length <= max(TOL, p["wall"] * 0.10):
            continue

        # Perpendicular/off-plane lines are still available for legs/3D bars.
        d0 = abs(p0.sub(plane["origin"]).dot(plane["normal"]))
        d1 = abs(p1.sub(plane["origin"]).dot(plane["normal"]))
        if d0 > tolerance or d1 > tolerance:
            continue

        # An outer perimeter edge has both endpoints on the same polygon side.
        if _edge_is_on_outer_perimeter(edge, plane, tolerance):
            continue

        uv0 = _plane_uv(p0, plane)
        uv1 = _plane_uv(p1, plane)
        clipped = _clip_segment_to_convex_polygon(uv0, uv1, polygon, tolerance)
        if clipped is None:
            continue
        uv0, uv1 = clipped

        direction = _canonical_direction_2d((uv1[0] - uv0[0], uv1[1] - uv0[1]))
        if direction is None:
            continue
        normal2d = (-direction[1], direction[0])
        offset = normal2d[0] * uv0[0] + normal2d[1] * uv0[1]
        t0 = direction[0] * uv0[0] + direction[1] * uv0[1]
        t1 = direction[0] * uv1[0] + direction[1] * uv1[1]

        group = None
        for candidate in groups:
            if abs(_cross2(direction, candidate["direction"])) > angle_tolerance:
                continue
            if abs(offset - candidate["offset"]) > tolerance:
                continue
            group = candidate
            break
        if group is None:
            group = {
                "direction": direction,
                "normal": normal2d,
                "offset": offset,
                "intervals": [],
                "sources": [],
                "edge_keys": set(),
            }
            groups.append(group)
        group["intervals"].append((t0, t1))
        group["sources"].append(edge.get("source"))
        group["edge_keys"].add(edge_key(edge))
        used_keys.add(edge_key(edge))

    members = []
    member_keys = set()

    for group in groups:
        # A crossing/grid can split one straight line into several geometries.
        intervals = _merge_scalar_intervals(group["intervals"], tolerance * 2.0)
        direction = group["direction"]
        normal2d = group["normal"]
        offset = group["offset"]

        for t0, t1 in intervals:
            if t1 - t0 <= max(TOL, p["profile_width"] * 0.25):
                continue
            uv_start = (
                direction[0] * t0 + normal2d[0] * offset,
                direction[1] * t0 + normal2d[1] * offset,
            )
            uv_end = (
                direction[0] * t1 + normal2d[0] * offset,
                direction[1] * t1 + normal2d[1] * offset,
            )
            center_start = _plane_point(uv_start, plane)
            center_end = _plane_point(uv_end, plane)
            raw = center_end.sub(center_start)
            if raw.Length <= max(TOL, p["profile_width"] * 0.25):
                continue
            axis_x = vector_unit(raw)

            # If a drawn endpoint is on the outer centerline, trim it to the
            # inner face. Interior endpoints remain exactly where they were drawn.
            start_attachment = loop_side_attachment(center_start, plane, tolerance * 3.0)
            end_attachment = loop_side_attachment(center_end, plane, tolerance * 3.0)
            trim_start = 0.0
            trim_end = 0.0
            if start_attachment is not None:
                trim_start = max(0.0, trim_to_inner_face(
                    axis_x, start_attachment["side_index"], plane,
                    p["profile_width"], True,
                ))
            if end_attachment is not None:
                trim_end = max(0.0, trim_to_inner_face(
                    axis_x, end_attachment["side_index"], plane,
                    p["profile_width"], False,
                ))
            trim_start = min(trim_start, raw.Length * 0.45)
            trim_end = min(trim_end, raw.Length * 0.45)
            length = raw.Length - trim_start - trim_end
            if length <= max(TOL, p["profile_width"] * 0.50):
                continue

            center_start = center_start.add(axis_x.multiply(trim_start))
            center_end = center_start.add(axis_x.multiply(length))
            axis_z = App.Vector(plane["normal"])
            axis_y_raw = axis_z.cross(axis_x)
            if axis_y_raw.Length <= TOL:
                continue
            axis_y = vector_unit(axis_y_raw)
            origin = center_start.sub(axis_y.multiply(p["profile_width"] / 2.0))

            key = tuple(sorted((
                quantized_point(center_start, 1e3),
                quantized_point(center_end, 1e3),
            )))
            if key in member_keys:
                continue
            member_keys.add(key)

            leg_positions = _vertical_leg_positions_on_member(
                all_edges, center_start, center_end, plane, tolerance * 3.0
            )
            members.append({
                "kind": "planar_raw_sketch",
                "index": 0,
                "start": origin,
                "end": origin.add(axis_x.multiply(length)),
                "length": length,
                "axis_x": axis_x,
                "axis_y": axis_y,
                "axis_z": axis_z,
                "footprint": [
                    (0.0, 0.0),
                    (length, 0.0),
                    (length, p["profile_width"]),
                    (0.0, p["profile_width"]),
                ],
                "internal_member": True,
                "network_member": True,
                "raw_sketch_member": True,
                "start_leg": bool(leg_positions and leg_positions[0] <= tolerance * 2.0),
                "end_leg": bool(leg_positions and leg_positions[-1] >= length - tolerance * 2.0),
                "leg_positions": leg_positions,
                "source": group["sources"][0] if group["sources"] else None,
            })

    return members, used_keys




def _outer_cycle_edge_keys(plane):
    """Arestas consecutivas do ciclo externo, em coordenadas globais."""
    keys = set()
    vertices = list(plane.get("vertices", []))
    for index in range(len(vertices)):
        a = App.Vector(vertices[index])
        b = App.Vector(vertices[(index + 1) % len(vertices)])
        keys.add(tuple(sorted((quantized_point(a), quantized_point(b)))))
    return keys


def _v427p_segment_intersection(a0, a1, b0, b1, tolerance=1e-8):
    """Interseção simples de dois segmentos 2D, sem criar Shapes."""
    da = sub2d(a1, a0)
    db = sub2d(b1, b0)
    denominator = cross2d(da, db)

    if abs(denominator) <= tolerance:
        return None

    delta = sub2d(b0, a0)
    ta = cross2d(delta, db) / denominator
    tb = cross2d(delta, da) / denominator

    if not (-tolerance <= ta <= 1.0 + tolerance):
        return None
    if not (-tolerance <= tb <= 1.0 + tolerance):
        return None

    return ta, tb


def _v427p_merge_intervals(intervals, length, tolerance=1e-6):
    clipped = []
    for a, b in intervals:
        start = max(0.0, min(float(a), float(b)))
        end = min(float(length), max(float(a), float(b)))
        if end - start > tolerance:
            clipped.append((start, end))

    if not clipped:
        return []

    clipped.sort(key=lambda item: item[0])
    result = [list(clipped[0])]

    for start, end in clipped[1:]:
        if start <= result[-1][1] + tolerance:
            result[-1][1] = max(result[-1][1], end)
        else:
            result.append([start, end])

    return [tuple(item) for item in result]


def _v427p_remaining_intervals(length, removed, minimum_length):
    removed = _v427p_merge_intervals(removed, length)
    result = []
    cursor = 0.0

    for start, end in removed:
        if start - cursor >= minimum_length:
            result.append((cursor, start))
        cursor = max(cursor, end)

    if length - cursor >= minimum_length:
        result.append((cursor, length))

    return result


def detect_orientable_planar_members(sources, plane, p):
    """
    Leitura mínima baseada diretamente na V4.27 original.

    Não procura novos quadros, não projeta a rede e não faz clipping global.
    Apenas:
    - mantém exatamente o início e o fim desenhados;
    - apara pontas que chegam ao quadro externo;
    - em T, a travessa termina na face do membro contínuo;
    - em cruzamento completo, o membro maior passa e o menor é dividido.
    """
    if plane is None:
        return [], set()

    all_edges = extract_all_edges(sources)
    perimeter_keys = _outer_cycle_edge_keys(plane)
    tolerance = max(p["attach_tolerance"], PLANAR_TOL * 50.0, 0.50)
    axis_z = vector_unit(App.Vector(plane["normal"]))

    candidates = []
    used_keys = set()
    canonical_edges = set()

    for order, edge in enumerate(all_edges):
        key = edge_key(edge)
        if key in perimeter_keys:
            continue

        p0 = App.Vector(edge["p0"])
        p1 = App.Vector(edge["p1"])
        raw = p1.sub(p0)
        raw_length = raw.Length

        if raw_length <= max(TOL, p["wall"] * 0.10):
            continue

        # Linhas verticais e linhas de outros níveis permanecem disponíveis
        # para o leitor original de pernas/rede 3D.
        d0 = abs(p0.sub(plane["origin"]).dot(plane["normal"]))
        d1 = abs(p1.sub(plane["origin"]).dot(plane["normal"]))
        if d0 > tolerance or d1 > tolerance:
            continue

        axis_x = vector_unit(raw)

        # Mantém o recuo de ponta aprovado na V4.27 original.
        start_attachment = loop_side_attachment(p0, plane, tolerance * 3.0)
        end_attachment = loop_side_attachment(p1, plane, tolerance * 3.0)
        trim_start = 0.0
        trim_end = 0.0

        if start_attachment is not None:
            trim_start = max(0.0, trim_to_inner_face(
                axis_x,
                start_attachment["side_index"],
                plane,
                p["profile_width"],
                True,
            ))

        if end_attachment is not None:
            trim_end = max(0.0, trim_to_inner_face(
                axis_x,
                end_attachment["side_index"],
                plane,
                p["profile_width"],
                False,
            ))

        trim_start = min(trim_start, raw_length * 0.45)
        trim_end = min(trim_end, raw_length * 0.45)

        center_start = p0.add(vector_scaled(axis_x, trim_start))
        center_end = p1.sub(vector_scaled(axis_x, trim_end))
        trimmed = center_end.sub(center_start)
        length = trimmed.Length

        if length <= max(TOL, p["profile_width"] * 0.50):
            continue

        axis_x = vector_unit(trimmed)
        start_uv = _plane_uv(center_start, plane)
        end_uv = _plane_uv(center_end, plane)
        direction_uv, uv_length = normalize2d(sub2d(end_uv, start_uv))

        canonical = tuple(sorted((
            quantized_point(center_start, 1e3),
            quantized_point(center_end, 1e3),
        )))
        if canonical in canonical_edges:
            continue
        canonical_edges.add(canonical)

        candidates.append({
            "order": order,
            "key": key,
            "source": edge.get("source"),
            "start": center_start,
            "end": center_end,
            "start_uv": start_uv,
            "end_uv": end_uv,
            "direction_uv": direction_uv,
            "length": min(length, uv_length),
            "axis_x": axis_x,
            "removed": [],
        })
        used_keys.add(key)

    App.Console.PrintMessage(
        "V4.27R mapa: {} linha(s) interna(s) encontrada(s).\\n".format(
            len(candidates)
        )
    )

    if len(candidates) > MAX_PLANAR_MEMBER_CANDIDATES:
        raise ValueError(
            "O esqueleto possui {} linhas internas candidatas; o limite seguro é {}. "
            "Selecione apenas o Sketch/Grupo da mesa e una traços fragmentados antes de gerar."
            .format(len(candidates), MAX_PLANAR_MEMBER_CANDIDATES)
        )

    # Apenas cruzamentos reais entre as linhas já reconhecidas.
    endpoint_tolerance = 1e-5
    clearance = max(0.05, p.get("fit_clearance", 0.0) * 0.25)

    for first_index in range(len(candidates)):
        first = candidates[first_index]

        for second_index in range(first_index + 1, len(candidates)):
            second = candidates[second_index]
            hit = _v427p_segment_intersection(
                first["start_uv"], first["end_uv"],
                second["start_uv"], second["end_uv"],
            )
            if hit is None:
                continue

            t_first, t_second = hit
            sine_angle = abs(cross2d(
                first["direction_uv"], second["direction_uv"]
            ))
            if sine_angle <= 1e-5:
                continue

            first_inside = endpoint_tolerance < t_first < 1.0 - endpoint_tolerance
            second_inside = endpoint_tolerance < t_second < 1.0 - endpoint_tolerance
            first_endpoint = not first_inside
            second_endpoint = not second_inside
            half_gap = (p["profile_width"] * 0.5) / sine_angle + clearance

            # Junção em T: a linha que termina encosta na face do membro que
            # continua. Não divide o membro contínuo.
            if first_inside and second_endpoint:
                branch = second
                branch_t = t_second
                if branch_t <= 0.5:
                    branch["removed"].append((0.0, min(branch["length"], half_gap)))
                else:
                    branch["removed"].append((
                        max(0.0, branch["length"] - half_gap),
                        branch["length"],
                    ))
                continue

            if second_inside and first_endpoint:
                branch = first
                branch_t = t_first
                if branch_t <= 0.5:
                    branch["removed"].append((0.0, min(branch["length"], half_gap)))
                else:
                    branch["removed"].append((
                        max(0.0, branch["length"] - half_gap),
                        branch["length"],
                    ))
                continue

            # Pontas que apenas coincidem não exigem recorte adicional.
            if not first_inside or not second_inside:
                continue

            # Cruzamento completo: o maior passa. Em empate, mantém a ordem
            # original do Sketch para obter resultado determinístico.
            length_tolerance = max(1e-4, p["wall"] * 0.01)
            if first["length"] > second["length"] + length_tolerance:
                cut = second
                cut_t = t_second
            elif second["length"] > first["length"] + length_tolerance:
                cut = first
                cut_t = t_first
            elif first["order"] <= second["order"]:
                cut = second
                cut_t = t_second
            else:
                cut = first
                cut_t = t_first

            center = cut_t * cut["length"]
            cut["removed"].append((center - half_gap, center + half_gap))

    members = []
    generated_segments = set()
    minimum_piece = max(p["profile_width"] * 0.55, p["wall"] * 2.0)

    for candidate in candidates:
        intervals = _v427p_remaining_intervals(
            candidate["length"], candidate["removed"], minimum_piece
        )

        for piece_index, (u0, u1) in enumerate(intervals, start=1):
            length = u1 - u0
            if length <= minimum_piece:
                continue

            center_start = App.Vector(candidate["start"]).add(
                vector_scaled(candidate["axis_x"], u0)
            )
            center_end = App.Vector(candidate["start"]).add(
                vector_scaled(candidate["axis_x"], u1)
            )

            canonical = tuple(sorted((
                quantized_point(center_start, 1e3),
                quantized_point(center_end, 1e3),
            )))
            if canonical in generated_segments:
                continue
            generated_segments.add(canonical)

            axis_x = App.Vector(candidate["axis_x"])
            axis_y_raw = axis_z.cross(axis_x)
            if axis_y_raw.Length <= TOL:
                continue
            axis_y = vector_unit(axis_y_raw)
            origin = center_start.sub(
                vector_scaled(axis_y, p["profile_width"] * 0.5)
            )
            midpoint = center_start.add(
                vector_scaled(axis_x, length * 0.5)
            )

            leg_positions = _vertical_leg_positions_on_member(
                all_edges,
                center_start,
                center_end,
                plane,
                tolerance * 3.0,
            )

            members.append({
                "kind": "planar_orientable_member",
                "index": 0,
                "start": origin,
                "end": App.Vector(origin).add(vector_scaled(axis_x, length)),
                "length": length,
                "axis_x": axis_x,
                "axis_y": axis_y,
                "axis_z": axis_z,
                "footprint": [
                    (0.0, 0.0),
                    (length, 0.0),
                    (length, p["profile_width"]),
                    (0.0, p["profile_width"]),
                ],
                # Mantém o gerador completo e aprovado da V4.27.
                "internal_member": False,
                "line_member": True,
                "network_member": True,
                "orientable_member": True,
                "leg_positions": leg_positions,
                "start_leg": bool(
                    leg_positions and leg_positions[0] <= tolerance * 2.0
                ),
                "end_leg": bool(
                    leg_positions
                    and leg_positions[-1] >= length - tolerance * 2.0
                ),
                "source": candidate["source"],
                "centerline_start": center_start,
                "centerline_end": center_end,
                "centerline_midpoint": midpoint,
                "map_piece": "{}:{}".format(
                    candidate["order"] + 1,
                    piece_index,
                ),
            })

    # Evita um travamento silencioso quando o Sketch gera uma quantidade
    # explosiva de trechos por duplicações ou cruzamentos acidentais.
    maximum_members = 120
    if len(members) > maximum_members:
        raise ValueError(
            "O mapa produziu {} trechos internos. O limite seguro é {}. "
            "Verifique linhas duplicadas ou cruzamentos muito próximos."
            .format(len(members), maximum_members)
        )

    App.Console.PrintMessage(
        "V4.27R mapa: {} trecho(s) estrutural(is) após os encontros.\\n".format(
            len(members)
        )
    )
    return members, used_keys


def detect_missing_planar_members_fallback(
    sources,
    plane,
    p,
    existing_members,
):
    """
    Segunda leitura, deliberadamente simples, usando a receita original da
    V4.27. Ela não substitui o mapa de cruzamentos; apenas garante que nenhuma
    linha coplanar desenhada desapareça do resultado.

    Isso cobre especialmente o caso: retângulo externo + uma travessa central
    em outro Sketch do mesmo Grupo.
    """
    if plane is None:
        return [], set()

    all_edges = extract_all_edges(sources)
    perimeter_keys = _outer_cycle_edge_keys(plane)
    tolerance = max(p["attach_tolerance"], PLANAR_TOL * 50.0, 0.50)
    axis_z = vector_unit(App.Vector(plane["normal"]))

    existing_keys = set()
    for member in existing_members:
        start = member.get("centerline_start")
        end = member.get("centerline_end")
        if start is None or end is None:
            continue
        existing_keys.add(tuple(sorted((
            quantized_point(start, 1e3),
            quantized_point(end, 1e3),
        ))))

    members = []
    used_keys = set()

    for edge in all_edges:
        key = edge_key(edge)
        if key in perimeter_keys:
            continue

        p0 = App.Vector(edge["p0"])
        p1 = App.Vector(edge["p1"])
        raw = p1.sub(p0)
        raw_length = raw.Length

        if raw_length <= max(TOL, p["wall"] * 0.10):
            continue

        d0 = abs(p0.sub(plane["origin"]).dot(plane["normal"]))
        d1 = abs(p1.sub(plane["origin"]).dot(plane["normal"]))
        if d0 > tolerance or d1 > tolerance:
            continue

        midpoint_raw = p0.add(raw.multiply(0.5))
        if not point_inside_projected_polygon(midpoint_raw, plane):
            continue

        axis_x_initial = vector_unit(raw)
        start_attachment = loop_side_attachment(
            p0, plane, tolerance * 3.0
        )
        end_attachment = loop_side_attachment(
            p1, plane, tolerance * 3.0
        )
        trim_start = 0.0
        trim_end = 0.0

        if start_attachment is not None:
            trim_start = max(0.0, trim_to_inner_face(
                axis_x_initial,
                start_attachment["side_index"],
                plane,
                p["profile_width"],
                True,
            ))

        if end_attachment is not None:
            trim_end = max(0.0, trim_to_inner_face(
                axis_x_initial,
                end_attachment["side_index"],
                plane,
                p["profile_width"],
                False,
            ))

        trim_start = min(trim_start, raw_length * 0.45)
        trim_end = min(trim_end, raw_length * 0.45)

        center_start = App.Vector(p0).add(
            vector_scaled(axis_x_initial, trim_start)
        )
        center_end = App.Vector(p1).sub(
            vector_scaled(axis_x_initial, trim_end)
        )
        trimmed = center_end.sub(center_start)
        member_length = trimmed.Length

        if member_length <= max(TOL, p["profile_width"] * 0.50):
            continue

        axis_x = vector_unit(trimmed)
        axis_y_raw = axis_z.cross(axis_x)
        if axis_y_raw.Length <= TOL:
            continue
        axis_y = vector_unit(axis_y_raw)

        canonical = tuple(sorted((
            quantized_point(center_start, 1e3),
            quantized_point(center_end, 1e3),
        )))
        if canonical in existing_keys:
            used_keys.add(key)
            continue

        existing_keys.add(canonical)
        used_keys.add(key)
        midpoint = App.Vector(center_start).add(
            vector_scaled(axis_x, member_length * 0.5)
        )
        origin = App.Vector(center_start).sub(
            vector_scaled(axis_y, p["profile_width"] * 0.5)
        )
        leg_positions = _vertical_leg_positions_on_member(
            all_edges,
            center_start,
            center_end,
            plane,
            tolerance * 3.0,
        )

        members.append({
            "kind": "planar_orientable_member_fallback",
            "index": 0,
            "start": origin,
            "end": App.Vector(origin).add(
                vector_scaled(axis_x, member_length)
            ),
            "length": member_length,
            "axis_x": axis_x,
            "axis_y": axis_y,
            "axis_z": axis_z,
            "footprint": [
                (0.0, 0.0),
                (member_length, 0.0),
                (member_length, p["profile_width"]),
                (0.0, p["profile_width"]),
            ],
            # Travessa detectada dentro do quadro: usa as quatro chapas físicas
            # no modo seguro, sem aplicar a receita pesada de dentes/rasgos do
            # perímetro externo. Isso preserva a estrutura e evita dezenas de
            # booleanas que não pertencem a uma ligação interna.
            "internal_member": True,
            "line_member": True,
            "network_member": True,
            "orientable_member": True,
            "fallback_member": True,
            "leg_positions": leg_positions,
            "start_leg": bool(
                leg_positions
                and leg_positions[0] <= tolerance * 2.0
            ),
            "end_leg": bool(
                leg_positions
                and leg_positions[-1]
                >= member_length - tolerance * 2.0
            ),
            "source": edge.get("source"),
            "centerline_start": center_start,
            "centerline_end": center_end,
            "centerline_midpoint": midpoint,
        })

    return members, used_keys


def detect_single_sketch_direct_members(source, plane, p):
    """Promove diretamente linhas internas de um único Sketch a travessas."""
    if source is None or not is_sketch(source) or plane is None:
        return []

    edges = extract_from_sketch(source)
    tolerance = max(p["attach_tolerance"], PLANAR_TOL * 50.0, 0.50)
    members = []
    seen = set()

    for edge in edges:
        p0 = App.Vector(edge["p0"])
        p1 = App.Vector(edge["p1"])
        raw = p1.sub(p0)
        if raw.Length <= max(TOL, p["wall"] * 0.10):
            continue
        if (
            abs(p0.sub(plane["origin"]).dot(plane["normal"])) > tolerance
            or abs(p1.sub(plane["origin"]).dot(plane["normal"])) > tolerance
        ):
            continue
        if _edge_is_on_outer_perimeter(edge, plane, tolerance):
            continue

        midpoint = p0.add(raw.multiply(0.5))
        if not point_inside_projected_polygon(midpoint, plane):
            continue

        axis_x = vector_unit(raw)
        start_attachment = loop_side_attachment(p0, plane, tolerance * 3.0)
        end_attachment = loop_side_attachment(p1, plane, tolerance * 3.0)
        trim_start = 0.0
        trim_end = 0.0
        if start_attachment is not None:
            trim_start = max(0.0, trim_to_inner_face(
                axis_x, start_attachment["side_index"], plane,
                p["profile_width"], True,
            ))
        if end_attachment is not None:
            trim_end = max(0.0, trim_to_inner_face(
                axis_x, end_attachment["side_index"], plane,
                p["profile_width"], False,
            ))
        trim_start = min(trim_start, raw.Length * 0.45)
        trim_end = min(trim_end, raw.Length * 0.45)
        length = raw.Length - trim_start - trim_end
        if length <= max(TOL, p["profile_width"] * 0.50):
            continue

        # Não escalar ``axis_x`` diretamente: Vector.multiply é mutável no
        # FreeCAD e deixaria o placement desta travessa dependente da ordem de
        # cálculo das duas pontas.
        center_start = p0.add(vector_scaled(axis_x, trim_start))
        center_end = center_start.add(vector_scaled(axis_x, length))
        axis_z = App.Vector(plane["normal"])
        axis_y_raw = axis_z.cross(axis_x)
        if axis_y_raw.Length <= TOL:
            continue
        axis_y = vector_unit(axis_y_raw)
        origin = center_start.sub(
            vector_scaled(axis_y, p["profile_width"] / 2.0)
        )

        key = tuple(sorted((
            quantized_point(center_start, 1e3),
            quantized_point(center_end, 1e3),
        )))
        if key in seen:
            continue
        seen.add(key)

        members.append({
            "kind": "single_sketch_direct",
            "index": 0,
            "start": origin,
            "end": App.Vector(origin).add(vector_scaled(axis_x, length)),
            "length": length,
            "axis_x": axis_x,
            "axis_y": axis_y,
            "axis_z": axis_z,
            "footprint": [
                (0.0, 0.0),
                (length, 0.0),
                (length, p["profile_width"]),
                (0.0, p["profile_width"]),
            ],
            "internal_member": True,
            "network_member": True,
            "raw_sketch_member": True,
            "single_sketch_direct": True,
            "start_leg": False,
            "end_leg": False,
            "leg_positions": _vertical_leg_positions_on_member(
                edges, center_start, center_end, plane, tolerance * 3.0
            ),
            "source": source,
        })

    return members


def configure_internal_member_connections(members, p):
    """Reserva passagens de pernas/tocos e posiciona costelas de abraço."""
    leg_w, leg_d = leg_dimensions(p)
    toco_w, toco_d = toco_dimensions(p)
    opening_depth = min(
        p["profile_width"] * 0.82,
        max(p["wall"] * 2.0, leg_w, leg_d, toco_w, toco_d),
    )
    clearance = max(p["rib_clearance"], p["rib_slot_clearance"])

    for descriptor in members:
        length = descriptor["length"]
        openings = []
        blocked = []
        hugs = []

        positions = list(descriptor.get("leg_positions", []))
        if descriptor.get("start_leg", False) and not positions:
            positions.append(0.0)
        if descriptor.get("end_leg", False) and not positions:
            positions.append(length)

        for position in unique_scalar_centers(positions):
            if position <= opening_depth / 2.0:
                open_start, open_end = 0.0, min(length, opening_depth)
                hug_candidates = [open_end + clearance + p["rib_thickness"] / 2.0]
            elif position >= length - opening_depth / 2.0:
                open_start, open_end = max(0.0, length - opening_depth), length
                hug_candidates = [open_start - clearance - p["rib_thickness"] / 2.0]
            else:
                half = opening_depth / 2.0
                open_start = max(0.0, position - half)
                open_end = min(length, position + half)
                hug_candidates = [
                    open_start - clearance - p["rib_thickness"] / 2.0,
                    open_end + clearance + p["rib_thickness"] / 2.0,
                ]

            openings.append((open_start, open_end))
            blocked.append((
                max(0.0, open_start - p["rib_thickness"]),
                min(length, open_end + p["rib_thickness"]),
            ))
            for center in hug_candidates:
                if p["rib_thickness"] / 2.0 < center < length - p["rib_thickness"] / 2.0:
                    hugs.append(center)

        descriptor["lower_openings"] = merge_intervals(openings, 0.0, length)
        descriptor["rib_blocked_intervals"] = merge_intervals(blocked, 0.0, length)
        descriptor["local_hug_rib_centers"] = unique_scalar_centers(hugs)
        descriptor["connection_rib_centers"] = []
        descriptor["suppress_regular_ribs"] = False


def point_inside_projected_polygon(point, plane):
    delta = point.sub(plane["origin"])
    px = delta.dot(plane["axis_u"])
    py = delta.dot(plane["axis_v"])
    vertices = plane["projected"]
    inside = False
    j = len(vertices) - 1
    for i in range(len(vertices)):
        xi, yi = vertices[i]
        xj, yj = vertices[j]
        crosses = ((yi > py) != (yj > py)) and (
            px < (xj - xi) * (py - yi) / ((yj - yi) or 1e-12) + xi
        )
        if crosses:
            inside = not inside
        j = i
    return inside


def line_plane_intersection(edge, plane):
    direction = edge["p1"].sub(edge["p0"])
    denominator = direction.dot(plane["normal"])
    if abs(denominator) <= TOL:
        return None
    parameter = plane["origin"].sub(edge["p0"]).dot(plane["normal"]) / denominator
    if parameter < -1e-6 or parameter > 1.0 + 1e-6:
        return None
    return edge["p0"].add(direction.multiply(parameter))


def nearest_loop_side(point, plane):
    best = None
    for index in range(len(plane["vertices"])):
        start = plane["vertices"][index]
        end = plane["vertices"][(index + 1) % len(plane["vertices"])]
        t, projected, distance = project_point_to_segment(point, start, end)
        candidate = (distance, index, projected)
        if best is None or candidate[0] < best[0]:
            best = candidate
    return best


def intermediate_toco_contacts(network_edges, frames, p):
    """Localiza cruzamentos de linhas estruturais com quadros intermediários."""
    contacts = []
    seen = set()
    tolerance = max(p["attach_tolerance"], p["profile_width"] * 0.55)

    for frame_index, frame in enumerate(frames, start=1):
        plane = frame["plane"]
        for edge in network_edges:
            contact = line_plane_intersection(edge, plane)
            if contact is None:
                continue
            nearest = nearest_loop_side(contact, plane)
            if nearest is None:
                continue
            distance, side_index, projected = nearest
            # Aceita contato na moldura ou dentro dela; o toco é preso ao lado mais próximo.
            if distance > tolerance and not point_inside_projected_polygon(contact, plane):
                continue
            key = (frame_index,) + quantized_point(projected, scale=1e3)
            if key in seen:
                continue
            seen.add(key)
            side_start = plane["vertices"][side_index]
            side_end = plane["vertices"][(side_index + 1) % len(plane["vertices"])]
            side_vector = side_end.sub(side_start)
            side_length = side_vector.Length
            if side_length <= TOL:
                continue
            side_axis = side_vector.multiply(1.0 / side_length)
            side_u = clamp(
                projected.sub(side_start).dot(side_axis),
                0.0, side_length
            )
            contacts.append({
                "frame_index": frame_index,
                "plane": plane,
                "point": App.Vector(projected),
                "side_index": side_index,
                "side_u": side_u,
            })
    return contacts


def apply_intermediate_toco_connections(frames, contacts, p):
    """
    Abre o painel inferior ao redor do toco e cria duas costelas locais,
    uma de cada lado. Quadros secundários não recebem a distribuição
    automática de costelas; recebem apenas esses abraços necessários.
    """
    if not frames:
        return

    toco_w, _toco_d = toco_dimensions(p)
    opening_half = toco_w / 2.0 + p["toco_clearance"] + p["rib_slot_clearance"]
    hug_offset = (
        opening_half
        + p["rib_thickness"] / 2.0
        + max(p["rib_clearance"], p["rib_slot_clearance"])
    )

    for frame in frames:
        for descriptor in frame["segments"]:
            descriptor["suppress_regular_ribs"] = True
            descriptor.setdefault("local_hug_rib_centers", [])

    for contact in contacts:
        frame_index = int(contact["frame_index"]) - 1
        if frame_index < 0 or frame_index >= len(frames):
            continue
        frame = frames[frame_index]
        side_index = int(contact["side_index"])
        if side_index < 0 or side_index >= len(frame["segments"]):
            continue
        descriptor = frame["segments"][side_index]
        length = descriptor["length"]
        u = clamp(float(contact.get("side_u", 0.0)), 0.0, length)

        descriptor.setdefault("lower_openings", []).append((
            max(0.0, u - opening_half),
            min(length, u + opening_half),
        ))
        descriptor.setdefault("rib_blocked_intervals", []).append((
            max(0.0, u - hug_offset - p["rib_thickness"]),
            min(length, u + hug_offset + p["rib_thickness"]),
        ))

        for center in (u - hug_offset, u + hug_offset):
            if (
                center > p["rib_thickness"] / 2.0 + TOL
                and center < length - p["rib_thickness"] / 2.0 - TOL
            ):
                descriptor.setdefault("local_hug_rib_centers", []).append(center)

        descriptor["local_hug_rib_centers"] = unique_scalar_centers(
            descriptor.get("local_hug_rib_centers", [])
        )



def create_intermediate_tocos(doc, root, contacts, p):
    if not contacts or not toco_enabled(p):
        return 0

    parent = doc.addObject("App::Part", "Conexoes_Toco_Intermediarias")
    parent.Label = "Conexões intermediárias por toco local"
    mark_generated(parent)
    root.addObject(parent)

    toco_w, toco_d = toco_dimensions(p)
    plate_t = toco_plate_thickness(p)
    count = max(1, int(p["toco_plate_count"]))
    created = 0

    for contact_index, contact in enumerate(contacts, start=1):
        plane = contact["plane"]
        side_index = contact["side_index"]
        start = plane["vertices"][side_index]
        end = plane["vertices"][(side_index + 1) % len(plane["vertices"])]
        axis_x = vector_unit(end.sub(start))
        axis_z = App.Vector(plane["normal"])
        axis_y = vector_unit(axis_z.cross(axis_x))
        origin = contact["point"]
        placement = matrix_placement(origin, axis_x, axis_y, axis_z)

        # O toco fica dentro da moldura, encostado à face inferior do quadro.
        x0 = -toco_w / 2.0
        y0 = p["wall"] + p["toco_clearance"]
        for plate_index in range(1, count + 1):
            z0 = p["profile_height"] - p["wall"] - plate_index * plate_t
            shape = Part.makeBox(
                toco_w, toco_d, plate_t,
                App.Vector(x0, y0, z0),
            )
            create_shape_feature(
                doc, parent,
                "Toco_Intermediario_{:02d}_{:02d}".format(
                    contact_index, plate_index
                ),
                "Toco local {:02d} — chapa {:02d}/{:02d}".format(
                    contact_index, plate_index, count
                ),
                shape, placement,
            )
            created += 1
    return created


def interpret_geometry_preferred_contour(all_edges, contour_edges, p):
    """
    Quando há múltiplos objetos de origem, prioriza o SketchOrigem
    como limite externo. Isso evita que travessas/cortes internos
    interfiram na detecção do quadro principal.
    """
    if not contour_edges:
        return None

    nodes, graph_edges, adjacency = build_graph(contour_edges)
    cycle = find_simple_planar_cycle(nodes, graph_edges, adjacency)
    if cycle is None:
        return None

    contour_keys = {
        edge_key(contour_edges[idx])
        for idx in cycle["edge_ids"]
    }

    remaining_edges = [
        edge for edge in all_edges
        if edge_key(edge) not in contour_keys
    ]

    plane = plane_basis(
        cycle["vertices"],
        remaining_edges,
        p["height_direction"],
    )
    planar_segments = calculate_planar_segments(
        plane,
        p["profile_width"],
        p["connection"],
    )

    mode_result = (
        "Híbrido: contorno preferencial + elementos 3D"
        if remaining_edges else
        "Contorno externo planar"
    )

    return {
        "mode_result": mode_result,
        "plane": plane,
        "planar_segments": planar_segments,
        "network_edges": remaining_edges,
    }


def interpret_geometry(edges, p):
    nodes, graph_edges, adjacency = build_graph(edges)
    all_edge_ids = set(range(len(graph_edges)))

    if p["mode"] == "Rede 3D por eixos":
        return {
            "mode_result": "Rede 3D por eixos",
            "plane": None,
            "planar_segments": [],
            "network_edges": edge_records_from_ids(
                all_edge_ids,
                graph_edges,
            ),
        }

    cycle = find_simple_planar_cycle(
        nodes,
        graph_edges,
        adjacency,
    )

    if cycle is None:
        if p["mode"] == "Contorno externo planar":
            raise ValueError(
                "As linhas não formam um contorno fechado simples."
            )

        return {
            "mode_result": "Rede 3D por eixos",
            "plane": None,
            "planar_segments": [],
            "network_edges": edge_records_from_ids(
                all_edge_ids,
                graph_edges,
            ),
        }

    cycle_ids = set(cycle["edge_ids"])
    remaining_ids = all_edge_ids.difference(cycle_ids)
    remaining_edges = edge_records_from_ids(
        remaining_ids,
        graph_edges,
    )

    if p["mode"] == "Contorno externo planar" and remaining_edges:
        raise ValueError(
            "No modo Contorno externo planar, remova as linhas que não "
            "pertencem ao contorno ou use o modo Automático."
        )

    plane = plane_basis(
        cycle["vertices"],
        remaining_edges,
        p["height_direction"],
    )
    planar_segments = calculate_planar_segments(
        plane,
        p["profile_width"],
        p["connection"],
    )

    if remaining_edges:
        mode_result = "Híbrido: contorno externo + elementos 3D"
    else:
        mode_result = "Contorno externo planar"

    return {
        "mode_result": mode_result,
        "plane": plane,
        "planar_segments": planar_segments,
        "network_edges": remaining_edges,
    }


# =============================================================================
# Resultados e execução
# =============================================================================

def update_results(
    params,
    interpretation,
    planar_count,
    network_count,
    anchored_count,
    corner_leg_count,
    edge_leg_count,
    total_ribs,
    total_caps,
    total_toco_plates,
    total_cap_ribs,
    total_shoulders,
    total_frame_teeth,
    total_leg_teeth,
):
    definitions = (
        ("App::PropertyString", "ModoDetectado", "Modo geométrico usado."),
        ("App::PropertyInteger", "NumeroSegmentosPlanares", "Lados do quadro."),
        ("App::PropertyInteger", "NumeroElementos3D", "Linhas 3D convertidas."),
        ("App::PropertyInteger", "NumeroPernasAncoradas", "Total de pernas conectadas."),
        ("App::PropertyInteger", "NumeroPernasCanto", "Pernas ligadas a vértices."),
        ("App::PropertyInteger", "NumeroPernasIntermediarias", "Pernas ligadas ao meio de uma lateral."),
        ("App::PropertyInteger", "TotalCostelasCalculado", "Costelas internas geradas."),
        ("App::PropertyInteger", "TotalTampasPernas", "Tampas internas geradas."),
        ("App::PropertyInteger", "TotalOmbrosApoio", "Ombros externos de apoio gerados."),
        ("App::PropertyInteger", "TotalChapasToco", "Chapas de toco geradas."),
        ("App::PropertyInteger", "TotalTampasCostela", "Tampas-costela geradas."),
        ("App::PropertyInteger", "TotalDentesQuadro", "Dentes longitudinais gerados no quadro."),
        ("App::PropertyInteger", "TotalDentesPernas", "Dentes longitudinais gerados nas pernas."),
        ("App::PropertyString", "ConfirmacaoLimiteExterno", "Regra dimensional."),
        ("App::PropertyString", "ResumoMontagem", "Resumo das escolhas."),
    )
    for type_id, name, description in definitions:
        add_property(params, type_id, name, "09 — Resultado", description)

    params.ModoDetectado = interpretation["mode_result"]
    params.NumeroSegmentosPlanares = planar_count
    params.NumeroElementos3D = network_count
    params.NumeroPernasAncoradas = anchored_count
    params.NumeroPernasCanto = corner_leg_count
    params.NumeroPernasIntermediarias = edge_leg_count
    params.TotalCostelasCalculado = total_ribs
    params.TotalTampasPernas = total_caps
    params.TotalOmbrosApoio = total_shoulders
    params.TotalChapasToco = total_toco_plates
    params.TotalTampasCostela = total_cap_ribs
    params.TotalDentesQuadro = total_frame_teeth
    params.TotalDentesPernas = total_leg_teeth
    params.ConfirmacaoLimiteExterno = (
        "Quadro preserva o limite externo desenhado."
        if planar_count else
        "Sem quadro fechado: linhas 3D usadas como eixos."
    )
    params.ResumoMontagem = (
        "Quadro: {} | pernas: {} | apoio: {} | costelas: {} | "
        "rasgos de costelas: {} | alívio: {}".format(
            str(params.UniaoPaineisQuadro),
            "{} / {}".format(str(params.ConexaoPernaQuadro), str(params.UniaoPaineisPerna)),
            "{} / {}".format(str(params.ApoioSuperiorPerna), str(params.ApoioPainelInferiorNoPe)),
            str(params.MontagemCostelas),
            "sim" if bool(params.GerarRasgosReais) else "não",
            "{}; furos reais costelas: {}".format(
                str(params.AlivioCantosRasgos),
                "sim" if bool(params.GerarFurosReaisCostelas) else "não",
            ),
        )
    )
    set_read_only(params, (
        "ModoDetectado",
        "NumeroSegmentosPlanares",
        "NumeroElementos3D",
        "NumeroPernasAncoradas",
        "NumeroPernasCanto",
        "NumeroPernasIntermediarias",
        "TotalCostelasCalculado",
        "TotalTampasPernas",
        "TotalOmbrosApoio",
        "TotalChapasToco",
        "TotalTampasCostela",
        "TotalDentesQuadro",
        "TotalDentesPernas",
        "ConfirmacaoLimiteExterno",
        "ResumoMontagem",
    ))


def build(doc, params, sources):
    p = read_parameters(params)
    edges = extract_all_edges(sources)

    interpretation = None
    preferred_contour = getattr(params, "SketchOrigem", None)
    contour_edges = None

    if p["mode"] != "Rede 3D por eixos" and len(sources) > 1:
        # Primeiro tenta o link explícito, desde que realmente forme um ciclo.
        if preferred_contour in sources:
            try:
                candidate_edges = extract_all_edges([preferred_contour])
                nodes_c, graph_c, adjacency_c = build_graph(candidate_edges)
                if find_simple_planar_cycle(nodes_c, graph_c, adjacency_c) is not None:
                    contour_edges = candidate_edges
            except Exception:
                contour_edges = None

        # Caso o link esteja incorreto, escolhe automaticamente o maior ciclo.
        if contour_edges is None:
            preferred_contour, contour_edges = find_best_contour_source(sources)
            if preferred_contour is not None:
                try:
                    params.SketchOrigem = preferred_contour
                except Exception:
                    pass

        if contour_edges is not None:
            interpretation = interpret_geometry_preferred_contour(
                edges, contour_edges, p
            )

    if interpretation is None:
        interpretation = interpret_geometry(edges, p)

    # V4.27: uma única leitura para qualquer linha coplanar não perimetral.
    # O mesmo gerador tubular usado nos quatro lados externos cria também
    # travessas, linhas de malha e membros inclinados no plano.
    internal_members, raw_internal_keys = detect_orientable_planar_members(
        sources, interpretation["plane"], p
    )

    # A leitura principal já entende todas as travessas.  A segunda leitura
    # antiga só entra como recuperação quando a primeira não encontrou membro
    # algum; rodá-la sempre duplicava trabalho e travava esboços fragmentados.
    if not internal_members:
        fallback_members, fallback_keys = detect_missing_planar_members_fallback(
            sources,
            interpretation["plane"],
            p,
            internal_members,
        )
        if fallback_members:
            internal_members.extend(fallback_members)
            raw_internal_keys.update(fallback_keys)
            App.Console.PrintWarning(
                "V4.27R: {} linha(s) coplanar(es) recuperada(s) pela leitura "
                "direta de segurança.\n".format(len(fallback_members))
            )

    secondary_frames = []
    secondary_keys = set()

    remaining_network_edges = [
        edge for edge in interpretation["network_edges"]
        if edge_key(edge) not in raw_internal_keys
    ]
    App.Console.PrintMessage(
        "V4.27R: {} membro(s) interno(s); {} origem(ns) processada(s).\n".format(
            len(internal_members), len(sources)
        )
    )

    clear_generated(doc)
    root = doc.addObject("App::Part", ROOT_NAME)
    root.Label = "Estrutura V4.27R — fabricação estável + travessas"
    mark_generated(root)
    if getattr(root, "ViewObject", None) is not None:
        root.ViewObject.Visibility = False

    network_descriptors, anchored_count, corner_leg_count, edge_leg_count = create_network_descriptors(
        remaining_network_edges, interpretation["plane"], p,
    )

    planar_segments = list(interpretation["planar_segments"])
    next_index = len(planar_segments) + 1
    for frame in secondary_frames:
        for descriptor in frame["segments"]:
            descriptor["index"] = next_index
            descriptor["intermediate_frame"] = True
            descriptor["suppress_regular_ribs"] = True
            descriptor["local_hug_rib_centers"] = []
            planar_segments.append(descriptor)
            next_index += 1

    for descriptor in internal_members:
        descriptor["index"] = next_index
        planar_segments.append(descriptor)
        next_index += 1

    planar_count = len(planar_segments)
    for descriptor in planar_segments:
        descriptor["trim_lower_start"] = False
        descriptor["trim_lower_end"] = False
        if not descriptor.get("internal_member", False):
            descriptor["lower_openings"] = []
            descriptor["rib_blocked_intervals"] = []
            descriptor["connection_rib_centers"] = []
            descriptor.setdefault("local_hug_rib_centers", [])

    configure_internal_member_connections(internal_members, p)

    # A rede planar usa as próprias linhas como estruturas. Pernas ligadas a
    # qualquer ponto da rede abrem passagem e recebem costelas de abraço.
    contacts = []

    primary_planar_count = len(interpretation["planar_segments"])
    primary_planar_segments = planar_segments[:primary_planar_count]

    if p["trim_frame_lower"] and upper_support_occupies_frame(p):
        leg_w, leg_d = leg_dimensions(p)

        if p.get("lower_panel_support") == "Não apoiar — encaixe livre":
            # Montagem livre aprovada: o fundo horizontal é interrompido
            # por toda a projeção externa da perna. Assim o quadro desce
            # ao redor do pé e o toco fica responsável apenas pelo travamento.
            support_w, support_d = leg_w, leg_d
            x_margin = 0.0
            y_margin = 0.0
        else:
            # No modo com ombro, somente o toco atravessa o painel inferior.
            support_w, support_d = support_opening_dimensions(p)
            support_w = min(support_w + 2.0 * p["rib_slot_clearance"], leg_w)
            support_d = min(support_d + 2.0 * p["rib_slot_clearance"], leg_d)
            x_margin = max(0.0, (leg_w - support_w) / 2.0)
            y_margin = max(0.0, (leg_d - support_d) / 2.0)
        for leg in network_descriptors:
            if leg["kind"] == "axis_corner" and planar_count:
                corner = leg["corner_index"]
                current = primary_planar_segments[corner]
                previous = primary_planar_segments[(corner - 1) % primary_planar_count]
                # Apenas o toco atravessa o painel inferior. O restante do painel
                # permanece sobre a perna e passa a ter apoio físico.
                current_opening = (x_margin, x_margin + support_w)
                previous_opening = (
                    previous["length"] - (y_margin + support_d),
                    previous["length"] - y_margin,
                )
                current["lower_openings"].append(current_opening)
                previous["lower_openings"].append(previous_opening)
                current["rib_blocked_intervals"].append((0.0, leg_w))
                previous["rib_blocked_intervals"].append((previous["length"] - leg_d, previous["length"]))
            elif leg["kind"] == "axis_edge":
                segment = primary_planar_segments[leg["edge_segment_index"]]
                half = support_w / 2.0
                opening = (leg["edge_u"] - half, leg["edge_u"] + half)
                segment["lower_openings"].append(opening)
                segment["rib_blocked_intervals"].append((
                    leg["edge_u"] - leg_w / 2.0 - p["rib_thickness"],
                    leg["edge_u"] + leg_w / 2.0 + p["rib_thickness"],
                ))
                if p.get("create_t_connection_rib", False):
                    segment["connection_rib_centers"].append(leg["edge_u"])

    total_ribs = 0
    total_caps = 0
    total_toco_plates = 0
    total_cap_ribs = 0
    total_shoulders = 0
    total_frame_teeth = 0
    total_leg_teeth = 0

    for descriptor in planar_segments:
        result = create_planar_segment(doc, root, descriptor, p)
        total_ribs += result["ribs"]
        total_frame_teeth += result["frame_teeth"]

    for result_index, descriptor in enumerate(network_descriptors, start=1):
        result = create_axis_segment(doc, root, descriptor, p, result_index)
        total_ribs += result["ribs"]
        total_caps += result["caps"]
        total_toco_plates += result["toco_plates"]
        total_cap_ribs += result["cap_ribs"]
        total_shoulders += result["shoulders"]
        total_leg_teeth += result["leg_teeth"]

    # Sem tocos locais extras: evita duplicação e peças projetadas para fora.

    update_results(
        params,
        interpretation,
        len(planar_segments),
        len(network_descriptors),
        anchored_count,
        corner_leg_count,
        edge_leg_count,
        total_ribs,
        total_caps,
        total_toco_plates,
        total_cap_ribs,
        total_shoulders,
        total_frame_teeth,
        total_leg_teeth,
    )

    for source in sources:
        try:
            source.Visibility = p["show_sources"]
        except Exception:
            pass
    doc.recompute()
    if getattr(root, "ViewObject", None) is not None:
        root.ViewObject.Visibility = True
    if Gui is not None:
        try:
            Gui.activeDocument().activeView().viewAxonometric()
        except Exception:
            pass

    App.Console.PrintMessage(
        "V4.24: {} lado(s), {} perna(s) de canto, {} intermediária(s), "
        "{} costela(s), {} tampa-costela(s), {} ombro(s), "
        "{} dente(s) do quadro e {} dente(s) das pernas.\n".format(
            len(planar_segments), corner_leg_count, edge_leg_count,
            total_ribs, total_cap_ribs, total_shoulders,
            total_frame_teeth, total_leg_teeth,
        )
    )


def main():
    App.Console.PrintMessage("\n=== V4.27R — FABRICAÇÃO ESTÁVEL + TRAVESSAS INTERNAS ===\n")
    doc = active_or_new_document()
    params = ensure_parameters(doc)
    sources = resolve_sources(params)
    doc.recompute()
    build(doc, params, sources)


try:
    main()
except Exception as exc:
    App.Console.PrintError(
        "Erro na V4.27R: {}\n".format(exc)
    )

    if Gui is not None:
        try:
            try:
                from PySide2 import QtWidgets
            except Exception:
                from PySide import QtGui as QtWidgets

            QtWidgets.QMessageBox.critical(
                None,
                "Gerador de estrutura por esqueleto v4",
                str(exc),
            )
        except Exception:
            pass

    raise
